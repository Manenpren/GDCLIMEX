(defun C:Tlayer ()
    (setq linea (car (entsel "Selecciona la linea : ")))
    (setq texto (car (entsel "Selecciona el BLOCK: ")))
    (setq layer (cdr (assoc 8 (entget LINEA))))
    (setq prov2 2)
    (while (/= "-" (substr LAYER prov2 1))
	(setq prov2(1+ prov2))
    )
    (setq NL (strcat (substr LAYER 1 (1- prov2)) "." (substr LAYER (1+ prov2) 3)))
    (SETQ BL (ENTNEXT TEXTO))
    (SETQ BL (ENTNEXT BL))
    (COMMAND "attedit" "" "" "" "" bl "V" "R" NL "")
)
