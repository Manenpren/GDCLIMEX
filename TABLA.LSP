(DEFUN SUMA (P VX VY)
  (SETQ X (CAR P))
  (SETQ Y (CAR (CDR P)))
  (LIST (+ X VX) (+ Y VY) (LAST P))
)

(DEFUN COLUMNAS ()
  (SETQ CA (SUBSTR LIN 1 1))
  (SETQ C 0) (SETQ X 1)
  (WHILE (/= CA "")
    (SETQ C (+ C 1))
    (SETQ DATO "")
    (WHILE (AND (/= CA ",") (/= CA ""))
      (SETQ X (+ X 1))
      (SETQ DATO (STRCAT DATO CA))
      (SETQ CA (SUBSTR LIN X 1))
    )
    (SETQ DATO (CONS (STRCAT (ITOA L) "-" (ITOA C)) DATO))
    (SETQ DATOS (APPEND DATOS (LIST DATO)))
    (SETQ CA (SUBSTR LIN (+ X 1) 1))
    (SETQ X (+ X 1))
  )
)

(DEFUN ANALIZA ()
  (SETQ NC 0) (SETQ LONTOT 0)
  (SETQ LONCOLS (LIST))
  (WHILE (/= NC C)
    (SETQ NC (+ NC 1))
    (SETQ NL 0) (SETQ LONG 0)
    (WHILE (/= NL L)
      (SETQ NL (+ NL 1))
      (SETQ CLAVE (STRCAT (ITOA NL) "-" (ITOA NC)))
      (IF (> (STRLEN (CDR (ASSOC CLAVE DATOS))) LONG)
        (SETQ LONG (STRLEN (CDR (ASSOC CLAVE DATOS))))
      )
    )
    (PRINC "\n")
    (SETQ M1 (STRCAT " LONGITUD MINIMA COLUMNA No. " (ITOA NC)))
    (SETQ M2 (STRCAT M1 "  " (ITOA (+ LONG 1)) " CARACTERES "))
    (PRINC M2)
    (SETQ LONCOL (GETINT "\n LONGITUD DE COLUMNA:  "))
    (SETQ LONCOLS (APPEND LONCOLS (LIST LONCOL)))
    (SETQ LONTOT (+ LONTOT LONCOL))
  )
  (SETQ TAM 1)
)

(DEFUN LEE ()
  (SETQ LIN (READ-LINE TBL))
  (SETQ L 1)
  (SETQ DATOS (LIST))
  (WHILE LIN 
    (COLUMNAS)
    (SETQ L (+ L 1))
    (SETQ LIN (READ-LINE TBL))
  )
  (SETQ L (- L 1))
  (ANALIZA)
  (CLOSE TBL)
)

(DEFUN LINEAS ()
  (SETQ LONGITUD (* LONTOT TAM))
  (SETQ EII (GETPOINT "\n ESQUINA INFERIOR IZQ. DE TABLA "))
  (SETVAR "CECOLOR" "1")
  (COMMAND "LINE" EII (POLAR EII 0 LONGITUD) "")
  (COMMAND "ARRAY" "LAST" "" "R" (+ L 1) 1 (* TAM 2))
  (SETVAR "CECOLOR" "BYLAYER")
  (COMMAND "LINE" EII (POLAR EII 1.5708 (* TAM 2 L)) "")
  (SETQ NC2 -1) (SETQ DIST 0)
  (COMMAND "ZOOM" "W" (SUMA EII TAM TAM) (SUMA EII (- TAM TAM TAM) (- TAM TAM TAM)))
  (WHILE (/= NC2 (- C 1))
    (SETQ NC2 (+ NC2 1))
    (SETQ DIST (+ DIST (* (NTH NC2 LONCOLS) TAM)))
    (COMMAND "OFFSET" DIST (POLAR EII 1.5708 TAM) (POLAR EII 0 TAM) "")
  )
  (COMMAND "ZOOM" "P")
)

(DEFUN COLOCA ()
  (SETQ NL 0)
  (WHILE (/= NL L)
    (SETQ NL (+ NL 1))
    (SETQ NC 0) (SETQ COLUMNA 0)
    (WHILE (/= NC C)
      (SETQ NC (+ NC 1))
      (SETQ CLAVE (STRCAT (ITOA NL) "-" (ITOA NC)))
      (SETQ EI (SUMA EII COLUMNA (* TAM (- L NL) 2)))
      (SETQ PBI (POLAR EI 0.785398 (/ TAM 1.2)))
      (IF (OR (= (ATOF (CDR (ASSOC CLAVE DATOS))) 0) (= NC 50))
        (COMMAND "INSERT" (strcat ruta "blocks\\TEXTO") PBI "" "" "")
        (COMMAND "INSERT" (strcat ruta "blocks\\NUMERO")
           (SUMA PBI (- (* (NTH (- NC 1) LONCOLS) TAM) 1) 0)
           "" "" ""
        )
      )
      (SETQ TM (* TAM 25))
      (SETQ BLOQUE (ENTLAST))
      (COMMAND "EXPLODE" BLOQUE)
      (SETQ E (ENTLAST))
      (ENTMOD (SUBST (CONS 1 (CDR (ASSOC CLAVE DATOS)))
                     (ASSOC 1 (ENTGET E))
                     (ENTGET E)
              )
      )
      (SETQ COLUMNA (+ COLUMNA (NTH (- NC 1) LONCOLS)))
    )
  )
)

(DEFUN SECUENCIA ()
  (LEE)
  (LINEAS)
  (COLOCA)
)

(DEFUN C:TABLA1 ()
  (setq NOMBRE (getfiled "ARCHIVO DE DATOS" "C:/TOPOGRAF/" "CSV" 18))
  (IF (SETQ TBL (OPEN NOMBRE "r"))
    (SECUENCIA)
    (PRINC "EL ARCHIVO NO EXISTE EN EL DIRECTORIO ")
  )
)
