;(setq version (getvar "acadver"))
;(if (/= version "14.0")
; (progn
;  (IF (= (SUBSTR (GETVAR "dwgname") 1 7) "Drawing")
;   (command "vslide" (strcat RUTAFAS "slides\\inicio2.sld"))
;   (command "vslide" (strcat RUTAFAS "slides\\inicio.sld"))
;  )
;  (Command "delay" "350" "redraw")
; )

;)

(SETQ RUTAFAS (STRCAT RUTA "FAS\\"))
(LOAD (STRCAT RUTA "REGISTRO"))
(setq arch1 (open (strcat ruta "RUTA.dll") "w"))
(write-line RUTA arch1)
(close arch1)

(DEFUN C:centroide ()
  (SETQ PROGRAMA "centroide")
  (C:REGISTRO)
  (C:LIBRERIA "CENTROIDE DE UN POLIGONO IRREGULAR2")
  (setq x (ax:centroid (car (entsel "\n Selecciona el poligono para sacar el centroide "))))
  (command "point" x)
)

(DEFUN C:dcarta ()
  (SETQ PROGRAMA "dibuja carta 1:50,000")
  (C:REGISTRO)
  (LOAD (STRCAT RUTAFAS "dibuja carta 50000"))
  (C:dibujac1)
)

(DEFUN C:ncarta ()
  (SETQ PROGRAMA "nombre de carta 1:50,000")
  (C:REGISTRO)
  (LOAD (STRCAT RUTAFAS "ncarta"))
  (C:ncarta1)
)

(DEFUN C:pgeo ()
  (SETQ PROGRAMA "coordenada geodesica")
  (C:REGISTRO)
  (LOAD (STRCAT RUTAFAS "pgeo"))
  (C:pgeo1)
)

(DEFUN C:LI ()
  (SETQ PROGRAMA "LIMPIA ARCHIVO Y MK CROQUIS")
  (C:REGISTRO)
  (LOAD (STRCAT RUTAFAS "LIMPIA ARCHIVO Y HAS CROQUIS"))
  (C:LIM)
)

(DEFUN C:curvas ()
  (SETQ PROGRAMA "Curvas")
  (C:REGISTRO)
  (LOAD (STRCAT RUTAFAS "curvas"))
  (C:curvas1)
)


(DEFUN C:dsec ()
  (SETQ PROGRAMA "dessec")
  (C:REGISTRO)
  (LOAD (STRCAT RUTAFAS "SEC"))
  (C:Dessec)
)

(DEFUN C:csec ()
  (SETQ PROGRAMA "creacfg")
  (C:REGISTRO)
  (LOAD (STRCAT RUTAFAS "SEC"))
  (C:creacfg)
)

(DEFUN c:HTEXT ()
  (SETQ PROGRAMA "ESCALA TEXTO")
  (C:REGISTRO)
  (LOAD (STRCAT RUTAFAS "HTEXT.fas"))
  (C:HTEXT1)
)

(DEFUN c:rtsc ()
  (SETQ PROGRAMA "rota y escala")
  (C:REGISTRO)
  (LOAD (STRCAT RUTAFAS "rotsca.fas"))
  (C:rotsca)
)

(DEFUN c:INVPL ()
  (SETQ PROGRAMA "INVIERTE POL")
  (C:REGISTRO)
  (LOAD (STRCAT RUTAFAS "INVIERTE SENTIDO DE POLYLINEA.fas"))
  (C:INVPOL)
)

(DEFUN c:PENDIENTE ()
  (SETQ PROGRAMA "PENDIENTE")
  (C:REGISTRO)
  (LOAD (STRCAT RUTAfas "PENDIENTE"))
  (C:PENDIENTE1)
)

(DEFUN c:CAD3 ()
  (SETQ PROGRAMA "CADENA3")
  (C:REGISTRO)
  (LOAD (STRCAT RUTAFAS "CADENA3.fas"))
  (C:CADENA3)
)

(DEFUN c:Prv ()
  (SETQ PROGRAMA "prov")
  (C:REGISTRO)
  (LOAD (STRCAT RUTAFAS "prov.fas"))
  (C:Prov)
)

(DEFUN c:PP ()
  (SETQ PROGRAMA "PIE DE PLANO CHAPALA")
  (C:REGISTRO)
  (LOAD (STRCAT RUTAFAS "PIE DE PLANO CHAPALA.fas"))
  (C:PP1)
)

(DEFUN c:iniv ()
  (SETQ PROGRAMA "iguala niveles")
  (C:REGISTRO)
  (LOAD (STRCAT RUTAFAS "iguala niveles"))
  (C:ign)
)

(DEFUN c:NIV ()
  (SETQ PROGRAMA "NIVELACION")
  (C:REGISTRO)
  (LOAD (STRCAT RUTAFAS "NIVELACION.fas"))
  (C:NIVELACION3)
)

(DEFUN c:ACOTA ()
  (SETQ PROGRAMA "ACOTA")
  (C:REGISTRO)
  (LOAD (STRCAT RUTAFAS "ACOTA"))
  (C:ACOT)
)

(DEFUN c:INTERPOLA2 ()
  (SETQ PROGRAMA "INTERPOLA 2 PUNTOS EN UNO")
  (C:REGISTRO)
  (LOAD (STRCAT RUTAFAS "INTERPOLA 2 PUNTOS"))
  (C:INTER)
)

(DEFUN c:INTERPOLA ()
  (SETQ PROGRAMA "INTERPOLA 2 PUNTOS")
  (C:REGISTRO)
  (LOAD (STRCAT RUTAFAS "INTERPOLA 2 PUNTOS"))
  (C:INTER2)
)

(DEFUN c:DYB ()
  (SETQ PROGRAMA "DYB")
  (C:REGISTRO)
  (LOAD (STRCAT RUTAFAS "IDY"))
  (C:DY1B)
)

(DEFUN c:PERFSURF ()
  (SETQ PROGRAMA "PERFSURF")
  (C:REGISTRO)
  (LOAD (STRCAT RUTAFAS "PERFSURF"))
  (C:PERFSURF1)
)

(DEFUN c:pel ()
  (SETQ PROGRAMA "pelev")
  (C:REGISTRO)
  (LOAD (STRCAT RUTAFAS "PELEV"))
  (C:PEL2)
)

(DEFUN c:CRLAY ()
  (SETQ PROGRAMA "CRLAY")
  (C:REGISTRO)
  (LOAD (STRCAT RUTAFAS "CRLAY"))
  (C:CRLA)
)

(DEFUN c:ESTACION ()
  (SETQ PROGRAMA "ESTACION")
  (C:REGISTRO)
  (LOAD (STRCAT RUTAFAS "ESTACION"))
  (C:ESTACION)
)

(DEFUN c:CONVIERTE ()
  (SETQ PROGRAMA "convierte pl")
  (C:REGISTRO)
  (LOAD (STRCAT RUTAFAS "COMVIERTE POLILINEAS"))
  (C:COMVIERTE)
)

(DEFUN C:PUNTOS ()
  (SETQ PROGRAMA "PUNTOS")
  (C:REGISTRO)
  (LOAD (STRCAT RUTAFAS "PUNTOS"))
  (C:PUNTS)
)

(DEFUN C:PERF ()
  (SETQ PROGRAMA "PERF")
  (C:REGISTRO)
  (LOAD (STRCAT RUTAFAS "PERF"))
  (C:PERF2)
)

(DEFUN C:ALINEA ()
  (SETQ PROGRAMA "ALINEA")
  (C:REGISTRO)
  (LOAD (STRCAT RUTAFAS "ALINEA"))
  (C:ALINSEC)
)

(DEFUN C:ARREGLO ()
  (SETQ PROGRAMA "ARREGLO")
  (C:REGISTRO)
  (LOAD (STRCAT RUTAFAS "ARREGLO"))
  (C:ARREGL)
)

(DEFUN C:ASOCIA ()
  (SETQ PROGRAMA "ASOCIA")
  (C:REGISTRO)
  (LOAD (STRCAT RUTA "ASOCIA"))
  (C:ASOC)
)

(DEFUN C:SBLOCK ()
  (SETQ PROGRAMA "SBLOCK")
  (C:REGISTRO)
  (LOAD (STRCAT RUTAFAS "SBLOCK"))
  (C:SBL)
)

(DEFUN C:IGUALB ()
  (SETQ PROGRAMA "IGUALA")
  (C:REGISTRO)
  (LOAD (STRCAT RUTAFAS "IGUALA"))
  (C:IGUAL)
)

(DEFUN C:BBLOCK ()
  (SETQ PROGRAMA "BBLOCK")
  (C:REGISTRO)
  (LOAD (STRCAT RUTAFAS "BBLOCK"))
  (C:BBL)
)

(DEFUN C:RBLOCK ()
  (SETQ PROGRAMA "RBLOCK")
  (C:REGISTRO)
  (LOAD (STRCAT RUTAFAS "RBLOCK"))
  (C:RBL)
)

(defun C:inicio ()
  (LOAD (STRCAT RUTAFAS "pdmodo"))
)

(DEFUN C:INSATR ()
  (SETQ PROGRAMA "INSATR")
  (C:REGISTRO)
  (LOAD (STRCAT RUTAFAS "INSATR"))
  (C:INSAT)
)

(DEFUN C:CADENA ()
  (SETQ PROGRAMA "CADENA2")
  (C:REGISTRO)
  (LOAD (STRCAT RUTAFAS "CADENA2"))
  (C:CADENA2)
)

(DEFUN C:CL ()
  (SETQ PROGRAMA "CALARE")
  (C:REGISTRO)
  (LOAD (STRCAT RUTAFAS "CALARE"))
  (C:CALAR)
)

(DEFUN C:CL2 ()
  (SETQ PROGRAMA "CALARE2")
  (C:REGISTRO)
  (LOAD (STRCAT RUTAFAS "CALARE2"))
  (C:CALAR2)
)

(DEFUN C:NUMBL ()
  (SETQ PROGRAMA "NUMBL")
  (C:REGISTRO)
  (LOAD (STRCAT RUTAFAS "CAMBIOB"))
  (C:CAM)
)

(DEFUN C:CADENAM ()
  (SETQ PROGRAMA "CAMCAD")
  (C:REGISTRO)
  (LOAD (STRCAT RUTAFAS "CAMCAD"))
  (C:CAMCAD)
)

(DEFUN C:CAMLAYER ()
  (SETQ PROGRAMA "CAMLAYER")
  (C:REGISTRO)
  (LOAD (STRCAT RUTAFAS "CAMLAYER"))
  (C:CAML)
)

(DEFUN C:CHN ()
  (SETQ PROGRAMA "CHN")
  (C:REGISTRO)
  (LOAD (STRCAT RUTAFAS "CHN"))
  (C:CHN2)
)

(DEFUN C:EPP ()
  (SETQ PROGRAMA "EPP")
  (C:REGISTRO)
  (LOAD (STRCAT RUTAFAS "EPP"))
  (C:EPP2)
)

(DEFUN C:ESCALA ()
  (SETQ PROGRAMA "ESCALA")
  (C:REGISTRO)
  (LOAD (STRCAT RUTAFAS "ESCALA"))
  (C:ESCALA2)
)

(DEFUN C:BUSE ()
  (SETQ PROGRAMA "ESTACION")
  (C:REGISTRO)
  (LOAD (STRCAT RUTAFAS "ESTACION"))
  (C:ESTACION)
)

(DEFUN C:DX ()
  (SETQ PROGRAMA "DX")
  (C:REGISTRO)
  (LOAD (STRCAT RUTAFAS "IDY"))
  (C:DX1)
)

(DEFUN C:DY ()
  (SETQ PROGRAMA "DY")
  (C:REGISTRO)
  (LOAD (STRCAT RUTAFAS "IDY"))
  (C:DY1)
)

(DEFUN C:INSPUN ()
  (SETQ PROGRAMA "INSPUN")
  (C:REGISTRO)
  (LOAD (STRCAT RUTAFAS "INSPUN"))
  (C:INSPUN1)
)

(DEFUN C:DELLAYER ()
  (SETQ PROGRAMA "DELLAYER")
  (C:REGISTRO)
  (LOAD (STRCAT RUTAFAS "DELLAYER"))
  (C:DELLAYER1)
)

(DEFUN C:RL ()
  (SETQ PROGRAMA "RL")
  (C:REGISTRO)
  (LOAD (STRCAT RUTAFAS "LAYERF"))
  (C:RL1)
)

(DEFUN C:ML ()
  (SETQ PROGRAMA "ML")
  (C:REGISTRO)
  (LOAD (STRCAT RUTAFAS "LAYERF"))
  (C:ML1)
)

(DEFUN C:LIMPIA ()
  (SETQ PROGRAMA "LIMPIA")
  (C:REGISTRO)
  (if (= (getvar "acadver") "14.0")
    (progn
      (LOAD (STRCAT RUTAFAS "LIMPIA14"))
      (C:LIMPI)
    )
    (progn
      (LOAD (STRCAT RUTAFAS "LIMPIA"))
      (C:LIMPI)
    )
  )
)

(DEFUN C:LMP ()
  (SETQ PROGRAMA "LIMPIACHP")
  (C:REGISTRO)
  (LOAD (STRCAT RUTAFAS "LIMPIACAHP"))
  (C:LIMPICH)
)

(DEFUN C:LINEA ()
  (SETQ PROGRAMA "LINEA")
  (C:REGISTRO)
  (LOAD (STRCAT RUTAFAS "LINEA"))
  (C:LINEA1)
)

(DEFUN C:LPF ()
  (SETQ PROGRAMA "LINTOPF")
  (C:REGISTRO)
  (LOAD (STRCAT RUTAFAS "LINTOPF"))
  (C:LP)
)

(DEFUN C:LPC ()
  (SETQ PROGRAMA "LINTOPCHAP")
  (C:REGISTRO)
  (LOAD (STRCAT RUTAFAS "LINTOPCHAP"))
  (C:LP)
)

(DEFUN C:POLVER ()
  (SETQ PROGRAMA "POLVER")
  (C:REGISTRO)
  (LOAD (STRCAT RUTAFAS "POLVER"))
  (C:POLVER1)
)

(DEFUN C:SE ()
  (SETQ PROGRAMA "SEC")
  (C:REGISTRO)
  (LOAD (STRCAT RUTAFAS "SEC"))
  (C:SE1)
)

(DEFUN C:TABLA ()
  (SETQ PROGRAMA "TABLA")
  (C:REGISTRO)
  (LOAD (STRCAT RUTAFAS "TABLA"))
  (C:TABLA1)
)

(DEFUN C:RTEXT ()
  (SETQ PROGRAMA "TEXTF")
  (C:REGISTRO)
  (LOAD (STRCAT RUTAFAS "TEXTF"))
  (C:RTEXT1)
)

(DEFUN C:IGUALA ()
  (SETQ PROGRAMA "IGUALA")
  (C:REGISTRO)
  (LOAD (STRCAT RUTAFAS "IGUALA"))
  (C:IGUAL)
)

(DEFUN C:IS5 ()
  (LOAD (STRCAT RUTAFAS "INSERTA5"))
  (C:INSERTA5)
)

(DEFUN C:txelev ()
  (LOAD (STRCAT RUTAFAS "telev"))
  (C:telev)
)

(SETQ RUTALIB RUTA)

(DEFUN C:LIBRERIA (LIBRERIA)
  (SETQ LIB (STRCAT RUTALIB "FUNCIONESc\\" LIBRERIA))
  (LOAD LIB)
)

(LOAD (STRCAT RUTAfas "1"))
(LOAD (STRCAT RUTAfas "RGS"))
(LOAD (STRCAT RUTAfas "ISSEC"))
(LOAD (STRCAT RUTAfas "BLOCKF"))
(LOAD (STRCAT RUTAfas "CA"))
