(defun c:wtx ()
  (command "undo" "m")
  (C:LIBRERIA "BUSCA VALOR DE ATRIBUTO")
  (C:LIBRERIA "AREA OBTENIDA EN UN PUNTO")
  (setq rutawb "c:\\topograf\\chapadr\\")
;  (SETQ RUTAWB2 (GETSTRING (STRCAT "\n RUTA A DESCARGAR <" RUTAWB "> :")))
  (IF (/= RUTAWB2 "") 
    (SETQ RUTAWB RUTAWB2)
  )
  (SETQ GPONOMNUM (SSADD))
  (SETQ GPONOMNUM (SSGET "X" '((2 . "NOMNUM"))))
  (SETQ E (SSNAME GPONOMNUM 0))
  (SETQ G 1)
  (WHILE E
;   (SETQ X (CAR PUNTO))
;   (IF (/= X 0)
;    (PROGN
     (SETQ XYZ2 (cdr (assoc 10 (entget E))))
     (SETQ NLOT (BUSATR E "NO_LOTE"))
     (IF (OR (= NLoT NIL) (= NLOT ""))
       (setq nlot (busatr e "NO-LOTE"))
     )
     (SETQ PROPT (BUSATR E "NOMBRE"))
     (COMMAND "ZOOM" "C" XYZ2 "400")
     (SETQ ATERR (AREAP XYZ2 ARP))
     (setq vol (car (entsel "\n BLOCK DE VOLUMENES")))
     (SETQ VCOR (BUSATR VOL "VCORTE"))
  (command "insert" (strcat ruta "BLOCKS\\AREASF.DWG") XYZ2 "" "" "0" "" "" "" "" "" "" "" "" "" "")           ;INSERTA AREAS Y VOLUMENES
  (setq blc (entlast))
  (setq blc (entnext blc))
  (COMMAND "attedit" "" "" "" "" blc "V" "R" VCOR "")
  (setq blc (entnext blc))
  (COMMAND "attedit" "" "" "" "" blc "V" "R" VCOR "")
  (setq blc (entnext blc))
  (COMMAND "attedit" "" "" "" "" blc "V" "R" PROPT "")
  (setq blc (entnext blc))
  (COMMAND "attedit" "" "" "" "" blc "V" "R" ATERR "")
  (setq blc (entnext blc))
  (COMMAND "attedit" "" "" "" "" blc "V" "R" NLOT "")
      

;     (SETQ P1 (SUMA XYZ2 -300 -300))
;     (SETQ P2 (SUMA XYZ2 -300 300))
;     (SETQ P3 (SUMA XYZ2 300 300))
;     (SETQ P4 (SUMA XYZ2 300 -300))
;     (command "wblock" (STRCAT RUTAWB "\\" NLOT ".DWG") "" "0,0,0" "CP" P1 P2 P3 P4 "" "")
;     (command "u")
;    )
;   )
  (SETQ E (SSNAME GPONOMNUM G))
  (SETQ G (1+ G))
  )
)

(defun SUMA (punto xx yy)
  (setq x (car punto))
  (setq y (car (cdr punto)))
  (setq xxx (+ x xx))
  (setq yyy (+ y yy))
  (list xxx yyy)
)
