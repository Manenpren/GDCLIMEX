(DEFUN ZBLOCK ()
  (C:LIBRERIA "BUCA LIMITES SECCION")
  (setq zoomb 1)
  (BLIMSEC ZOOMB)
  (if (> (abs (- ydmax yumax)) (abs (- xdmax ximax))) (setq ydmax (- yumax (abs (/ 2 (- xdmax ximax))))))
  (SETQ X1 (STRCAT (RTOS (- XIMAX 1)) "," (RTOS (+ YUMAX 1))))
  (SETQ X2 (STRCAT (RTOS (+ XDMAX 1)) "," (RTOS (- YDMAX 1))))
  (COMMAND "ZOOM" "W" X1 X2)
)
