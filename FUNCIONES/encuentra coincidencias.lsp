(defun coincidencias (lista1 lista2 ancho1 ancho2)
  (setq ancholinea (+ ancho1 ancho2))
  (setq repeticion1 (/ (strlen lista1) ancholinea))
  (setq repeticion2 (/ (strlen lista2) ancholinea))
  (setq contlc 1)
  (setq contlc2 1)
    (dos_getprogress "Trabajando" "encontrando coincidencias" (+ repeticion1 repeticion2))
  (setq listafinal1 "")
  (setq listafinal2 "")
  (while (and (<= contlc repeticion1) (<= contlc2 repeticion2))
    (setq dato1 (substr lista1 (1+ (* (1- contlc) ancholinea)) ancholinea))
    (setq dato2 (substr lista2 (1+ (* (1- contlc2) ancholinea)) ancholinea))
    (if (and (= (substr dato1 1 ancho1) (substr dato2 1 ancho1)) (/= (substr dato1 (1+ ancho1) ancho2) "xxxxxx") (/= (substr dato2 (1+ ancho1) ancho2) "xxxxxx")) (progn (setq listafinal1 (strcat listafinal1 dato1)) (setq listafinal2 (strcat listafinal2 dato2))))
    (while (and (<= contlc repeticion1) (<= contlc2 repeticion2) (/= (substr dato1 1 ancho1) (substr dato2 1 ancho1)))
      (if (< (atoi (substr dato1 1 ancho1)) (atoi (substr dato2 1 ancho1)))
        (progn 
          (setq contlc (1+ contlc))
          (setq dato1 (substr lista1 (1+ (* (1- contlc) ancholinea)) ancholinea))
        )
      ) 
      (if (< (atoi (substr dato2 1 ancho1)) (atoi (substr dato1 1 ancho1)))
        (progn 
          (setq contlc2 (1+ contlc2))
          (setq dato2 (substr lista2 (1+ (* (1- contlc2) ancholinea)) ancholinea))
        )
      ) 
      (if (and (= (substr dato1 1 ancho1) (substr dato2 1 ancho1)) (/= (substr dato1 (1+ ancho1) ancho2) "xxxxxx") (/= (substr dato2 (1+ ancho1) ancho2) "xxxxxx")) (progn (setq listafinal1 (strcat listafinal1 dato1)) (setq listafinal2 (strcat listafinal2 dato2))))
    )
(dos_getprogress (+ contlc2 contlc2))
    (setq contlc2 (1+ contlc2))
    (setq contlc (1+ contlc))
  )
  (dos_getprogress t)
  (setq resultado (strcat listafinal1 listafinal2))
)
