(DEFUN seccuad (listapod lx ly nx ny x1 y1 px py)
  (setq sx (fix (1+ (/ (- px x1) (/ lx nx)))))
  (setq sy (fix (1+ (/ (- py y1) (/ ly ny)))))
  (setq numerocelda (1- (+ sx  (* nx (1- sy)))))
  (setq celdasel (substr listapod (1+ (* numerocelda (/ (strlen listapod) (* nx ny)))) (/ (strlen listapod) (* nx ny))))
)

;listapod	cadena		lista de apodos para las celdas escritos de izquierda a derecha de arriba hacia abajo y con un ancho "n" pero constante en toda la cadena
;lx		nummero		longitud del rectangulo en la direccion x en pixeles
;ly		nummero		longitud del rectangulo en la direccion y en pixeles
;nx		nummero		numero de celdas existentes en x
;ny		nummero		numero de celdas existentes en y
;x1		numero		coordenada inicial del rectangulo en x
;y1		numero		coordenada inicial del rectangulo en y
;px		numero		pulsacion en coordenada x
;py		numero		pulsacion en coordenada y

;306307308309
;256257258259260261262263264265266267268269270271272273274275276277278279280281282283284285286287288289290291292293294295296297298299300301302303304305
;(setq listaprov "001002003004005006007008009010011012013014015016017018019020021022023024025026027028029030031032033034035036037038039040041042043044045046047048049050051052053054055056057058059060061062063064065066067068069070071072073074075076077078079080081082083084085086087088089090091092093094095096097098099100101102103104105106107108109110111112113114115116117118119120121122123124125126127128129130131132133134135136137138139140141142143144145146147148149150151152153154155156157158159160161162163164165166167168169170171172173174175176177178179180181182183184185186187188189190191192193194195196197198199200201202203204205206207208209210211212213214215216217218219220221222223224225226227228229230231232233234235236237238239240241242243244245246247248249250251252253254255")
;(seccuad listaprov 164 186 15 17 1282 4225 px py)

;(defun c:punto ()
;  (setq punto (getpoint "punto a escanear?: "))
;  (setq px (fix (car punto)))
;  (setq py (fix (cadr punto)))
;  (seccuad "001002003004005006007008009010011012013014015016017018019020021022023024025026027028029030031032033034035036037038039040041042043044045046047048049050051052053054055056057058059060061062063064065066067068069070071072073074075076077078079080081082083084085086087088089090091092093094095096097098099100101102103104105106107108109110111112113114115116117118119120121122123124125126127128129130131132133134135136137138139140141142143144145146147148149150151152153154155156157158159160161162163164165166167168169170171172173174175176177178179180181182183184185186187188189190191192193194195196197198199200201202203204205206207208209210211212213214215216217218219220221222223224225226227228229230231232233234235236237238239240241242243244245246247248249250251252253254255" 164.000 186.000 15 17 1286 4309 px py)
;)
