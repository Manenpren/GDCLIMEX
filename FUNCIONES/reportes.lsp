(Defun genrepcal()
(setq DATCLI (get_tile "DATOCLI"))
(setq DATOCLI (1+ (ATOI DATCLI)))
(setq DATFUE (substr(get_tile "DATFUE") 1 2))
(setq DATIP (substr(get_tile "DATIP") 1 2))
(setq inccorre (get_tile "inccorre"))
(setq repgen (open (strcat ruta "//Temporales//" "paramgenrep.rep") "w"))
(write-line (STRCAT (ITOA DATOCLI) DATFUE DATIP inccorre) repgen)
(close repgen) 
;(setq vacporc (leebdex (CAR VERPOLXXX) (SUBSTR procedencia 1 1) DATOSFT2 DATOSFT1 "VC"))
(setq repgen (open (strcat ruta "//Temporales//" "estcli.rep") "w"))
(setq contver 0)
       (repeat (length estaciones3)
         (setq data (assoc (1+ contver) estaciones3))
	 (setq ldat (cdr (assoc (1+ contver) matrizporcentajc2)))
	 (setq datocl (cdr (assoc 3 ldat)))
	 (setq vacporc (substr datocl 13 5))
	 (setq matrizdatos(leebdex (cadr data) "C" DATOCLI DATFUE DATIP))
	 (setq vectorc (length matrizdatos))
	 (setq i 0)
	 ;(if (OR(= DATFUE "AN")(= DATFUE "ME"))
	   ;(setq estad (open (strcat ruta "//Temporales//" (cadr data) "c.EST" ) "w"))
	   (setq estacion (cadr data))
	 ;  (if (< (atoi estacion) 10000)(setq estacion (strcat "0" (itoa(atoi estacion)))))
	   (setq estad (open (strcat ruta "//Temporales//" estacion "c.CSV" ) "w"))
	;  )
	 (write-line (strcat ",,,") estad)
	 (if (= DATFUE "AN")(write-line (strcat "Año,Dato") estad))
	 (if (= DATFUE "ME")(write-line (strcat "Año,Mes,Dato") estad))
	 (if (= DATFUE "ST")(write-line (strcat "Año,Mes,1,2,3,4,5,6,7,8,9,10,11,12,13,14,15,16,17,18,19,20,21,22,23,24,25,26,27,28,29,30,31") estad))
	 (while (< i vectorc)
	   (if (= DATFUE "AN")
	     (progn
	     (setq vector (nth i matrizdatos))
	     (setq adata (cdr(car vector)))
	     (setq ddata (cdr(car(cdr vector))))
	     (write-line (strcat adata "," (rtos ddata 2 3)) estad)
             )
	     )
	   (if (= DATFUE "ME")
	     (progn
	     (setq vector (nth i matrizdatos))
	     (setq adata (cdr(car vector)))
	     (setq mdata (cdr(car(cdr vector))))
	     (setq ddata (cdr(car(cdr(cdr vector)))))
	     (write-line (strcat adata "," mdata "," ddata) estad)
	     )
	    )
	   (if (= DATFUE "ST")
	     (progn
	     (setq vector (nth i matrizdatos))
	     (setq adata (cdr(car vector)))
	     (setq mdata (cdr(car(cdr vector))))
	     (setq n 2)
	     (setq ddata (cdr(nth n vector)))
	     (setq n (1+ n))
	     (while (< n 33)
	       (setq ddatap (cdr(nth n vector)))
	       (setq ddata (strcat ddata "," ddatap))
	       (setq n (1+ n))
	       )
	     (write-line (strcat adata "," mdata "," ddata) estad)
	     )
	    )
	 (setq i (1+ i))
	  )
	 (close estad)
         (write-line (strcat estacion "," (caddr data)","(cadddr data)"," vacporc) repgen)
         (setq contver (1+ contver))
        )
  (close repgen)
  (setq repgen (open (strcat ruta "//Temporales//" "esteric.rep") "w"))
  (setq contver 0)
       (repeat (length estaciones4)
         (setq data (assoc (1+ contver) estaciones4))
	 (setq ldat (cdr (assoc (1+ contver) matrizporcentaje2)))
	 (setq datocl (cdr (assoc 3 ldat)))
	 (setq  vacporc (substr datocl 13 5))
	 (setq matrizdatos(leebdex (cadr data) "E" DATOCLI DATFUE DATIP))
	 (setq vectorc (length matrizdatos))
	 (setq i 0)
	; (if (OR(= DATFUE "AN")(= DATFUE "ME"))
	 ;  (setq estad (open (strcat ruta "//Temporales//" (cadr data) "e.est" ) "w"))
	   (setq estacion (cadr data))
	 ;  (if (< (atoi estacion) 10000)(setq estacion (strcat "0" (itoa(atoi estacion)))))
	   (setq estad (open (strcat ruta "//Temporales//" estacion "e.CSV" ) "w"))
	  ;)
	 (write-line (strcat ",,,") estad)
	 (if (= DATFUE "AN")(write-line (strcat "Año,Dato") estad))
	 (if (= DATFUE "ME")(write-line (strcat "Año,Mes,Dato") estad))
	 (if (= DATFUE "ST")(write-line (strcat "Año,Mes,1,2,3,4,5,6,7,8,9,10,11,12,13,14,15,16,17,18,19,20,21,22,23,24,25,26,27,28,29,30,31") estad))
	 (while (< i vectorc)
	   (if (= DATFUE "AN")
	     (progn
	     (setq vector (nth i matrizdatos))
	     (setq adata (cdr(car vector)))
	     (setq ddata (cdr(car(cdr vector))))
	     (write-line (strcat adata "," (rtos ddata 2 3)) estad)
             )
	     )
	   (if (= DATFUE "ME")
	     (progn
	     (setq vector (nth i matrizdatos))
	     (setq adata (cdr(car vector)))
	     (setq mdata (cdr(car(cdr vector))))
	     (setq ddata (cdr(car(cdr(cdr vector)))))
	     (write-line (strcat adata "," mdata "," ddata) estad)
	     )
	    )
	   (if (= DATFUE "ST")
	     (progn
	     (setq vector (nth i matrizdatos))
	     (setq adata (cdr(car vector)))
	     (setq mdata (cdr(car(cdr vector))))
	     (setq n 2)
	     (setq ddata (cdr(nth n vector)))
	     (setq n (1+ n))
	     (while (< n 33)
	       (setq ddatap (cdr(nth n vector)))
	       (setq ddata (strcat ddata "," ddatap))
	       (setq n (1+ n))
	       )
	     (write-line (strcat adata "," mdata "," ddata) estad)
	     )
	    )
	 (setq i (1+ i))
	  )
          (write-line (strcat estacion "," (caddr data)","(cadddr data)"," vacporc) repgen)
         (setq contver (1+ contver))
	 (CLOSE estad)
        )
    (close repgen)
  (if (and(= inccorre "1")(/= resultadocorr "")(/= resultadocorr nil))(greportecorrel resultadocorr))
  (startapp "C:/Program Files (x86)/Microsoft Office/Office14/excel.exe"(strcat"C:/GDClimex/Temporales/Genera_rep.xlsm"))
  (startapp "C:/Program Files (x86)/Microsoft Office/Office12/excel.exe"(strcat"C:/GDClimex/Temporales/Genera_rep.xlsm"))
  (startapp "C:/Program Files/Microsoft Office/Office12/excel.exe"(strcat"C:/GDClimex/Temporales/Genera_rep.xlsm"))
  (startapp "C:/Program Files/Microsoft Office/Office14/excel.exe"(strcat"C:/GDClimex/Temporales/Genera_rep.xlsm"))
  (done_dialog)
)
	 
(defun dialogorep()
(setq dcl_id (load_dialog (strcat ruta "dialogos\\reporte.dcl")))
(new_dialog "rep" dcl_id)
(action_tile "accept" "(genrepcal)")
(set_tile "Incdata" "1")
(mode_tile "Incdata" 1)
(set_tile "ANUAL" "1")
(set_tile "MEDIOS" "1")
(if (/= resultadocorr nil)(progn(mode_tile "inccorre" 0)(set_tile "inccorre" "1")))
(start_dialog)
  )

(defun greportecorrel(resultadoscorrel)
(setq repgen (open (strcat ruta "//Temporales//" "correlacion.csv") "w"))
(write-line ",," repgen)
(write-line ",ESTACION1,ESTACION2,CORRELACION," repgen)
(SETQ ESTACION1 (SUBSTR resultadoscorrel 1 6))
(SETQ ESTACION2 (SUBSTR resultadoscorrel 7 6))
(SETQ COR (SUBSTR resultadoscorrel 13 8))
(SETQ i 21)
(while (and(/= COR "")(/= ESTACION1 nil)(/= ESTACION1 ""))
 (write-line (strcat "," ESTACION1 "," ESTACION2 "," COR ",") repgen)
   (SETQ ESTACION1 (SUBSTR resultadoscorrel i 6))
   (setq i (+ i 6))
   (SETQ ESTACION2 (SUBSTR resultadoscorrel i 6))
   (setq i (+ i 6))
   (SETQ COR (SUBSTR resultadoscorrel i 8))
   (setq i (+ i 8))
  )
 (close repgen)
  (if (= inccorre nil)
    (progn
  (startapp "C:/Program Files (x86)/Microsoft Office/Office14/excel.exe"(strcat"C:/GDClimex/Temporales/correlacion.csv"))
  (startapp "C:/Program Files (x86)/Microsoft Office/Office12/excel.exe"(strcat"C:/GDClimex/Temporales/correlacion.csv"))
  (startapp "C:/Program Files/Microsoft Office/Office12/excel.exe"(strcat"C:/GDClimex/Temporales/correlacion.csv"))
  (startapp "C:/Program Files/Microsoft Office/Office14/excel.exe"(strcat"C:/GDClimex/Temporales/correlacion.csv"))
  )
 ) 
)
