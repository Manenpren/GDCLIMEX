(DEFUN BUSACC (LISTAOBJD COORDX COORDY)
  (SETQ ACCIONE "")
  (SETQ CONTBUS 0)
  (WHILE (= ACCIONE "")
    (SETQ X1 (ATOI (SUBSTR LISTAOBJD (1+ (* CONTBUS 30)) 4)))
    (SETQ Y1 (ATOI (SUBSTR LISTAOBJD (+ 5 (* CONTBUS 30)) 4)))
    (SETQ X2 (ATOI (SUBSTR LISTAOBJD (+ 9 (* CONTBUS 30)) 4)))
    (SETQ Y2 (ATOI (SUBSTR LISTAOBJD (+ 13 (* CONTBUS 30)) 4)))
    (SETQ ACCIONX (SUBSTR LISTAOBJD (+ 17 (* CONTBUS 30)) 14))
    (IF (AND (< X1 COORDX) (> X2 COORDX) (< Y1 COORDY) (> Y2 COORDY)) (SETQ ACCIONE ACCIONX))
    (SETQ CONTBUS (1+ CONTBUS))
    (IF (> (* CONTBUS 30) (STRLEN LISTAOBJD)) (SETQ ACCIONE NIL))
  )
  (IF (/= ACCIONE NIL)
    (SETQ ACCIONE (vl-string-trim " " ACCIONE))
    (SETQ ACCIONE "SIN OBJETO")
  )
)

;LISTAOBJD	CADENA		LISTA DE DATOS DE CADENA CON NOMBRE DE LA ACCION ENCONTRADA Y CON DATOS DE COORDENADAS DE LAS ESQUINAS DE LOS OBJETOS EN EL BOTON
;FORMATO DE LA LISTA DE OBJETOS LONGITUD DE CADENA PARA LISTA 30 CARACTERES POR OBJETO
;COORX		ENTERO		DATO ENTERO DE LA COORDENADA PULSADA POR EL USUARIO
;COORY		ENTERO		DATO ENTERO DE LA COORDENADA PULSADA POR EL USUARIO
