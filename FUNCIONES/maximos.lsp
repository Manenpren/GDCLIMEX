(DEFUN maximos (cadenapr periodo datoclim fechaini)
  (C:LIBRERIA "CONVIERTE NUMERO EN CADENA")
  (if (= datoclim 1) (setq anchochr 6))
  (if (= datoclim 2) (setq anchochr 1))
  (if (= datoclim 3) (setq anchochr 6))
  (if (= datoclim 4) (setq anchochr 1))
  (if (= datoclim 5) (setq anchochr 1))
  (if (= datoclim 6) (setq anchochr 1))
  (if (= datoclim 7) (setq anchochr 5))
  (if (= datoclim 8) (setq anchochr 5))
  (if (= datoclim 9) (setq anchochr 5))
  (setq anchol (+ 11 (* 31 anchochr)))
  (setq nmeses (/ (strlen cadenapr) anchol))
  (setq caracterprov "")
  (repeat anchochr
    (setq caracterprov (strcat caracterprov "x"))
  )
  (setq fret fechaini)
  (if (= periodo "ME")
   (progn
     (setq contmeses 1)
     (setq contci 1)
     (setq maxmes "") 
     (repeat nmeses
       (setq ldat (substr cadenapr (1+ (* anchol (1- contci))) anchol))
       (if (/= fret (substr ldat 1 6))
         (progn
           (setq fretx (substr ldat 1 6))
           (while (/= fret fretx)
             (if (/= fret fretx)
               (progn
                 (setq fret (mesmas fret))
                 (setq contmeses (1+ contmeses))
               )
             )
           )
         )
       )
       (setq dmax (maximom ldat))
       (setq lineaf (strcat (ntocad contmeses 0 4) dmax))
       (setq maxmes (strcat maxmes lineaf))
       (setq contci (1+ contci))
     )
   )
  )
  (if (= periodo "MM")
   (progn
     (setq contci 1)
     (setq maxmes (strcat "0001" caracterprov "0002" caracterprov "0003" caracterprov "0004" caracterprov "0005" caracterprov "0006" caracterprov "0007" caracterprov "0008" caracterprov "0009" caracterprov "0010" caracterprov "0011" caracterprov "0012" caracterprov)) 
     (repeat nmeses
       (setq ldat (substr cadenapr (1+ (* anchol (1- contci))) anchol))
       (setq dmax (maximom ldat))
       (setq mes (substr ldat 5 2))
       (setq datoex (substr maxmes (1+ (* (1- (atoi mes)) (+ 4 anchochr))) anchochr))
       (if (= datoex caracterprov) (setq maxmes (strcat (substr maxmes 1 (* (1- (atoi mes)) anchochr)) dmax (substr maxmes (1+ (* (atoi mes) anchochr))))))     
       (if (and (/= datoex caracterprov) (< (atof datoex) (atof dmax))) (setq maxmes (strcat (substr maxmes 1 (* (1- (atoi mes)) anchochr)) dmax (substr maxmes (1+ (* (atoi mes) anchochr))))))     
       (setq contci (1+ contci))
     )
   )
  )
  (if (= periodo "AN")
   (progn
     (setq fret (substr fret 1 4))
     (setq contmeses 1)
     (setq contci 1)
     (setq maxmes nil)
     (setq maxamo "")
     (setq contmesx 0) 
     (repeat nmeses
       (setq ldat (substr cadenapr (1+ (* anchol (1- contci))) anchol))
       (setq dmax (maximom ldat))
       (if (= maxmes nil) (setq maxmes dmax))
       (if (/= dmax caracterprov)
         (progn
           (if (< (atof maxmes) (atof dmax)) (setq maxmes dmax))
           (setq contmesx (1+ contmesx))
           (setq ultimodat "s")
         )
         (setq ultimodat "n")
       )
       (if (AND (< (ATOI fret) (ATOI (substr ldat 1 4))) (/= fret (substr ldat 1 4)))
         (progn
           (if (or (and (= contmesx 12) (= ultimodat "n")) (= contmesx 13))
             (progn
               (setq lineaf (strcat (ntocad contmeses 0 4) maxmes)) 
               (setq maxamo (strcat maxamo lineaf))
             )
           )
           (setq contmesx 0)
	   (setq fret (ANMAS FRET)) 
           (setq contmeses (1+ contmeses))
           (WHILE (/= FRET (substr ldat 1 4))
             (setq fret (ANMAS FRET)) 
             (setq contmeses (1+ contmeses))
           )
           (setq maxmes dmax)
           (if (and (= (substr ldat 5 2) "01") (= ultimodat "s")) (setq contmesx 1))
         )
       )
       (setq contci (1+ contci))
     )
     (if (= contmesx 12)
       (progn
         (setq lineaf (strcat (ntocad contmeses 0 4) maxmes)) 
         (setq maxmes (strcat maxamo lineaf))
       )
       (setq maxmes maxamo)
     )
   )
  )
  (setq maxmes maxmes)
)

(defun maximom (cadenaf)
  (setq contmx 1)
  (setq maxx nil)
  (setq ndias (numerodias (substr cadenaf 1 6)))
  (setq datonulo "")
  (repeat ndias
    (setq chrprov (substr cadenaf (+ 7 (* anchochr (1- contmx))) anchochr))
    (if (/= chrprov caracterprov)
      (progn
        (if (= maxx nil) (setq maxx chrprov))
        (if (< (atof maxx) (atof chrprov)) (setq maxx chrprov))
      )
      (setq datonulo "s")
    )
    (setq contmx (1+ contmx))
  )
  (if (or (= maxx nil) (= datonulo "s"))
    (setq maxx caracterprov)
    (setq maxx maxx)
  )
)

(defun mesmas (fecha)
  (setq mes (substr fecha 5 2))
  (if (= mes "12")
    (progn
      (setq amo (1+ (atoi (substr fecha 1 4))))
      (setq fechaf (strcat (itoa amo) "01"))
    )
    (progn
      (setq fechaf (strcat (substr fecha 1 4) (NTOCAD (1+ (atoi (substr fecha 5 2))) 0 2)))
    )
  )
  (setq fechaf fechaf)
)

(defun anmas (fecha)
  (setq fechaf (itoa (1+ (atoi fecha))))
)
;periodo	cadena		anual, media mensual o mensual "AN" "MM" "ME"
;cadenapr	cadena		cadena fuente a procesar
;datoclim	entero		numero de dato climatologico a procesar
;fechaini	cadena		fecha de comienzo de los datos "198101"

;  (setq ArcCon (open "d:\\x.cli" "r"))
;  (setq lINEAfUENTE (read-line arcCon))
;  (close arcCon)
;  (setq prov (maximos lineafuente "AN" 1 "198712"))
