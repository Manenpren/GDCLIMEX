(DEFUN teststud (lista1 lista2 carx cary)
  (C:LIBRERIA "media ar")
  (C:LIBRERIA "calculo s cuadrada")
  (C:LIBRERIA "d grados de libertad")
  (setq n1 (/ (strlen lista1) (+ carx cary)))
  (setq n2 (/ (strlen lista2) (+ carx cary)))
  (setq media1 (mediaar lista1 carx cary))
  (setq media2 (mediaar lista2 carx cary))
  (setq s1 (scuad lista1 carx cary))
  (setq s2 (scuad lista2 carx cary))
  (setq u (+ n1 n2 -2))
  (print n1)
  (print n2)
  (print u)
  (setq d (dgradosl u))
  (setq d1 (atof (substr d 1 5)))
  (setq d2 (atof (substr d 6 6)))
  (setq td (/ (- media1 media2) (expt (* (/ (+ (* n1 s1) (* n2 s2)) u) (+ (/ 1.00 n1) (/ 1.00 n2))) (/ 1.00 2.00))))
  (if (<= (abs td) d1) (setq resultado "BIEN"))
  (if (> (abs td) d1) (setq resultado "ERR"))
  (setq reportelist2 NIL)
  (setq CONCATENADO (cons 1 (itoa n1)))
  (setq reportelist2 (append reportelist2 (list CONCATENADO)))
  (setq CONCATENADO (cons 2 (itoa n2)))
  (setq reportelist2 (append reportelist2 (list CONCATENADO)))
  (setq CONCATENADO (cons 3 (rtos d1 2 3)))
  (setq reportelist2 (append reportelist2 (list CONCATENADO)))
  (setq CONCATENADO (cons 4 (rtos d2 2 3)))
  (setq reportelist2 (append reportelist2 (list CONCATENADO)))
  (setq CONCATENADO (cons 5 (rtos td 2 3)))
  (setq reportelist2 (append reportelist2 (list CONCATENADO)))
  (IF (= RESULTADO "BIEN")
    (setq CONCATENADO (cons 6 "El resultado del test no encontro ningun error en los datos"))
    (setq CONCATENADO (cons 6 "Se encontro un cambio en la media entre los dos intervalos"))
  )
  (setq reportelist2 (append reportelist2 (list CONCATENADO)))
  (setq resultado resultado)
)

;(teststud "001320024500367004100050601004050120705503898" "0013200245003670041000506010040501207055" 3 2)
;lista		cadena		lista de datos en forma de cadena 
;carx		entero		ancho de caracteres en x
;cary		entero		ancho de caracteres en y
