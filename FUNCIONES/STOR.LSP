(DEFUN STOR (TEXTOCONVERTIR)
  (SETQ CARACTERES (vl-string->list TEXTOCONVERTIR))
  (SETQ LONGITUDC (length CARACTERES))
  (SETQ N 0)
  (SETQ PDECIMAL NIL)
  (SETQ NUMEROFINAL 0)
  (WHILE (= PDECIMAL NIL)
    (SETQ CARACTER (nth n CARACTERES))
    (IF (= CARACTER 46) (SETQ PDECIMAL N)) 
    (SETQ N (1+ N))
  )
  (SETQ N 0)
  (REPEAT LONGITUDC
    (SETQ CARACTER (nth n CARACTERES))
    (IF (/= N PDECIMAL) (SETQ NUMEROFINAL (+ NUMEROFINAL (* (ATOF (CHR CARACTER)) (EXPT 10.000000000000000 (- PDECIMAL N)))))) 
    (SETQ N (1+ N))
  )
  (SETQ NUMEROFINAL NUMEROFINAL)
)
