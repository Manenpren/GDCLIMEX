(defun leebd (estacion procedencia variable fechaini tipodat tipoproceso)
  (C:LIBRERIA "minimos")
  (C:LIBRERIA "maximos")
  (C:LIBRERIA "media")
  (C:LIBRERIA "porcentajes")
  (C:LIBRERIA "totales")
  (C:LIBRERIA "serie temporal diaria")
 ; (if (< (atoi estacion) 10000)(setq estacion (strcat "0" (itoa(atoi estacion)))))
      (if (= procedencia "C")
        (progn
          (setq diradicional "CLICOM")
          (setq extencion ".cli")
        )
        (progn
          (setq diradicional "ERIC")
          (setq extencion ".clk")
        )
      )
      (if (= variable 1) (progn (setq dirprim "\\evapora\\") (setq ndec 2) (setq anchochr 6)))
      (if (= variable 2) (progn (setq dirprim "\\granizo\\") (setq ndec 0) (setq anchochr 1)))
      (if (= variable 3) (progn (setq dirprim "\\hp\\") (setq ndec 2) (setq anchochr 6)))
      (if (= variable 4) (progn (setq dirprim "\\neblina\\") (setq ndec 0) (setq anchochr 1)))
      (if (= variable 5) (progn (setq dirprim "\\nublado\\") (setq ndec 0) (setq anchochr 1)))
      (if (= variable 6) (progn (setq dirprim "\\rayos\\") (setq ndec 0) (setq anchochr 1)))
      (if (= variable 7) (progn (setq dirprim "\\temp\\") (setq ndec 2) (setq anchochr 5)))
      (if (= variable 8) (progn (setq dirprim "\\tempmax\\") (setq ndec 2) (setq anchochr 5)))
      (if (= variable 9) (progn (setq dirprim "\\tempmin\\") (setq ndec 2) (setq anchochr 5)))
      (setq ldat1 "")
      (if (and (= procedencia "E") (/= optimizadiarioe nil)) (setq ldat1 (optimizabdiarios2 estacion variable)))
      (if (and (= procedencia "C") (/= optimizadiarioc nil)) (setq ldat1 (optimizabdiarios2 estacion variable)))
      (if (= ldat1 "")
        (progn      
          (dos_getcancel "LEYENDO BD" "LEYENDO DATOS POR FAVOR ESPERE...")
          (IF (not (dos_getcanceL)) (exit))
          (dos_encrypt (strcat ruta "BASES DE DATOS\\DATOS CLIMATOLOGICOS\\" diradicional dirprim estacion extencion) (strcat "4avEjsD8GlñOpwrpfvc3071fdA" estacion "Ga4TykP8G5Umo9Ye513"))
          (setq archIVOindice (open (strcat ruta "BASES DE DATOS\\DATOS CLIMATOLOGICOS\\" diradicional dirprim estacion extencion) "r"))
          (setq ldat1x (read-line archIVOindice))
          (close archivoindice)
          (dos_encrypt (strcat ruta "BASES DE DATOS\\DATOS CLIMATOLOGICOS\\" diradicional dirprim estacion extencion) (strcat "4avEjsD8GlñOpwrpfvc3071fdA" estacion "Ga4TykP8G5Umo9Ye513"))
          (dos_getcanceL t)
          (setq ldat1 (descompacta ldat1x))
          (if (= procedencia "E")
            (progn
              (if (= controlbdace nil) (setq controlbdace 1))
              (setq cadenaprov (strcat estacion (itoa variable)))
              (setq valorx (list (cons 1 cadenaprov) (cons 2 ldat1)))
              (setq CONCATENADO (cons controlbdace valorx)) 
              (setq optimizadiarioe (append optimizadiarioe (list CONCATENADO)))
              (setq controlbdace (1+ controlbdace))
            )
          )
          (if (= procedencia "C")
            (progn
              (if (= controlbdacc nil) (setq controlbdacc 1))
              (setq cadenaprov (strcat estacion (itoa variable)))
              (setq valorx (list (cons 1 cadenaprov) (cons 2 ldat1)))
              (setq CONCATENADO (cons controlbdacC valorx)) 
              (setq optimizadiarioC (append optimizadiarioC (list CONCATENADO)))
              (setq controlbdacc (1+ controlbdacc))
            )
          )
        )
      );if 
      (if (OR (= tipodat "AN") (= tipodat "ME") (= tipodat "MM"))
        (progn
          ;(PRINT LDAT1)
          (setq fechaini (substr fechaini 1 6))
          (if (= tipoproceso "MA") (setq ldat1 (maximos ldat1 tipodat variable fechaini)))
          (if (= tipoproceso "MI") (setq ldat1 (minimos ldat1 tipodat variable fechaini)))
          (if (= tipoproceso "ME") (setq ldat1 (media ldat1 tipodat variable fechaini)))
          (if (= tipoproceso "TO") (setq ldat1 (TOTALES ldat1 tipodat variable fechaini)))
          (if (= tipoproceso "VC") (setq ldat1 (PORCENTAJES ldat1 tipodat variable fechaini)))
          ;(setq datoguard ldat1)
          ;(PRINT tipodat)
          ;(PRINT variable)
          ;(PRINT fechaini)
          ;(print tipoproceso)
          (if (AND (OR (= variable 1) (= variable 3)) (OR (= tipoproceso "MA") (= tipoproceso "MI") (= tipoproceso "ME")))
            (SETQ CARY 6)
          )
          (if (AND (OR (= variable 7) (= variable 8) (= variable 9)) (OR (= tipoproceso "MA") (= tipoproceso "MI") (= tipoproceso "ME")) )
            (SETQ CARY 5)
          )
          (if (= tipoproceso "TO")
            (SETQ CARY 9)
          )
          (if (= tipoproceso "VC")
            (SETQ CARY 5)
          )
          (if (and (or (= variable 2) (= variable 4) (= variable 5) (= variable 6)) (/= tipoproceso "VC"))
            (SETQ CARY 1)
          )
        )
      )
      (if (= tipodat "ST") (setq ldat1 (tempdiaria ldat1 variable fechaini)))
      (if (= tipodat "ST")
        (PROGN
          (SETQ CARX 6)
          (SETQ CARY ANCHOCHR)
        )
        (SETQ CARX 4)
      )
  (setq ldat1 ldat1)
)

(defun optimizabdiarios2 (estacion variable)
  (if (= procedencia "C")
    (progn
      (setq contcig 1)
      (setq estaciong "000000")
      (setq scierto "")
      (while (and (or (/= estacion (substr estaciong 1 5)) (/= VARIABLE (ATOI (substr estaciong 6 1)))) (< contcig controlbdacc))
        (setq estaciong (cdr (car (cdr (assoc contcig optimizadiarioc)))))
        (if (and (= estacion (substr estaciong 1 5)) (= VARIABLE (ATOI (substr estaciong 6 1)))) (setq scierto "s"))
        (setq contcig (1+ contcig))
      )
      (IF (= scierto "s")
        (setq listadat (cdr (cadr (cdr (assoc (1- contcig) optimizadiarioc)))))
        (setq listadat "")
      )
    )
    (progn
      (setq contcig 1)
      (setq estaciong "000000")
      (setq scierto "")
      (while (and (or (/= estacion (substr estaciong 1 5)) (/= VARIABLE (ATOI (substr estaciong 6 1)))) (< contcig controlbdacE))
        (setq estaciong (cdr (car (cdr (assoc contcig optimizadiarioe)))))
        (if (and (= estacion (substr estaciong 1 5)) (= VARIABLE (ATOI (substr estaciong 6 1)))) (setq scierto "s"))
        (setq contcig (1+ contcig))
      )
      (IF (= scierto "s")
        (setq listadat (cdr (cadr (cdr (assoc (1- contcig) optimizadiarioe)))))
        (setq listadat "")
      )
    )
  )
  (setq listadat listadat)
)

;(leebd "16087" "C" 3 "190001" "ST" "")
;estacion	cadena		estacion a graficar
;procedencia	cadena		Clicom o erick
;variable	entero		variable climatica a graficar 1-9
;FECHAINI	CADENA		FECHA INICIAL A PROCESAR LOS DATOS DE LA GRAFICA formato de 4 6 o 8 caracteres segun se requiera
;tipodat	CADENA		tipo de datos a graficar "AN" "ME" "ST" "MM"
;tipoproceso	cadena		tipo de proceso a recibir la cadena (valores maximos, minimos, medios, totales, %vacios, serie temporal) "MA" "MI" "ME" "TO" "VC" "ST"
