(defun ldblpp (klist)
  (start_list klist 3 0)
  (end_list)
  (start_list klist 2 0)
  (add_list "PUN2")
  (end_list)
  (setq archdim (open (strcat ruta "prov.tmp") "w"))
  (write-line "PUN2" archdim)
  (setq contador 1)
  (SETQ PR NIL)
  (SETQ PROB (TBLNEXT "BLOCK" T))
  (WHILE PROB
    (SETQ NPROV (CDR (CAR (CDR PROB))))
    (IF (and (/= NPROV nil)  (/= (strcase nprov) "PUN2"))
     (progn
      (start_list klist 2 contador)
      (add_list nprov)
      (end_list)
      (write-line nprov archdim)
     )
    )
    (SETQ PROB (TBLNEXT "BLOCK"))
    (setq contador (1+ contador))
  )
  (close archdim)
  (SETq RESP (1- contador))
)
