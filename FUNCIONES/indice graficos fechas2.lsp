(DEFUN dibujaindicea (fechaini fechafin); fecha con solo años 4 caracteres
;  (slide_image 5 401 173 252 (STRCAT RUTA "SLIDES\\INDICE.SLD"))
  (setq nciclos (1+ (/ (- (atoi fechafin) (atoi fechaini)) 20)))
  (setq contci 1)
  (setq freti fechaini)
  (repeat nciclos
    (if (= contci 1)
      (progn
        (fill_image 14 (+ 291 (* 18 (1- contci))) 62 16 20)
        (stexto (strcat freti "-" (itoa (+ 19 (atoi freti)))) "romans" 12 14 (+ 292 (* 18 (1- contci))))
      )
      (stexto (strcat freti "-" (itoa (+ 19 (atoi freti)))) "romans" 12 14 (+ 292 (* 18 (1- contci))))
    )
    (setq freti (itoa (+ 20 (atoi freti))))
    (setq contci (1+ contci))
  )
  (dibujaindiceb fechaini fechafin)
)

(DEFUN dibujaindiceb (fechaini fechafin)
  (if (> (- (atoi fechafin) (atoi fechaini)) 20)
    (setq nciclos 20)
    (setq nciclos (- (atoi fechafin) (atoi fechaini)))
  )
  (setq nciclos (atoi (rtos (/ nciclos 2.00) 2 0)))
  (setq contci 1)
  (setq freti fechaini)
  (repeat nciclos
    (stexto freti "romans" 12 91 (+ 311 (* 18 (1- contci))))
    (if (/= freti fechafin)
      (stexto (itoa (+ 1 (atoi freti))) "romans" 12 133 (+ 311 (* 18 (1- contci))))
    )
    (setq freti (itoa (+ 2 (atoi freti))))
    (setq contci (1+ contci))
  )
)

(defun atzindice (fechaini fechafin indice)
  (setq finidc (itoa (+ (atoi fechaini) (* 20 (1- (atoi indice))))))
  (if (< (atoi finidc) (atoi fechafin))
    (progn
;      (fill_image 3 270 173 252 0)
;      (slide_image 3 270 173 252 (STRCAT RUTA "SLIDES\\INDICE.SLD"))
      (setq nciclos (1+ (/ (- (atoi fechafin) (atoi fechaini)) 20)))
      (setq contci 1)
      (setq freti fechaini)
      (repeat nciclos
        (if (= contci (atoi indice))
          (progn
            (fill_image 14 (+ 291 (* 18 (1- contci))) 62 16 20)
            (stexto (strcat freti "-" (itoa (+ 19 (atoi freti)))) "romans" 12 14 (+ 292 (* 18 (1- contci))))
          )
          (stexto (strcat freti "-" (itoa (+ 19 (atoi freti)))) "romans" 12 14 (+ 292 (* 18 (1- contci))))
        )
        (setq freti (itoa (+ 20 (atoi freti))))
        (setq contci (1+ contci))
      )
      (dibujaindiceb finidc fechafin)
    )
  )
)

(DEFUN dibujaindicea2 (fechaini fechafin); fecha con solo años 4 caracteres
;  (slide_image -100 270 150 200(STRCAT RUTA "SLIDES\\INDICE.SLD"))
  (setq nciclos (1+ (/ (- (atoi fechafin) (atoi fechaini)) 20)))
  (setq contci 1)
  (setq freti fechaini)
  (repeat nciclos
    (if (= contci 1)
      (progn
        (fill_image 9 (+ 405 (* 18 (1- contci))) 62 13 21)
        (if (= nciclos 1)
          (stexto (strcat freti "-" fechafin) "romans" 12 8 (+ 405 (* 18 (1- contci))))
          (stexto (strcat freti "-" (itoa (+ 19 (atoi freti)))) "romans" 12 8 (+ 405 (* 18 (1- contci))))
        )
      )
      (if (/= nciclos contci)
        (stexto (strcat freti "-" (itoa (+ 19 (atoi freti)))) "romans" 12 8 (+ 405 (* 18 (1- contci))))
        (stexto (strcat freti "-" fechafin) "romans" 12 8 (+ 405 (* 18 (1- contci))))
      )
    )
    (setq freti (itoa (+ 20 (atoi freti))))
    (setq contci (1+ contci))
  )
  (dibujaindiceb2 fechaini fechafin)
)

(DEFUN dibujaindiceb2 (fechaini fechafin)
  (if (> (- (atoi fechafin) (atoi fechaini)) 20)
    (setq nciclos 20)
    (setq nciclos (- (atoi fechafin) (atoi fechaini)))
  )
  (setq nciclos (atoi (rtos (/ nciclos 2.00) 2 0)))
  (setq contci 1)
  (setq freti fechaini)
  (repeat 10
    (fill_image 85 (+ 405 (* 18 (1- contci))) 31 12 252)
    (fill_image 127 (+ 405 (* 18 (1- contci))) 31 12 252)
    (setq contci (1+ contci))
  )
  (setq contci 1)
  (repeat nciclos
    (stexto freti "romans" 12 85 (+ 405 (* 18 (1- contci))))
    (if (/= freti fechafin)
      (progn
        (stexto (itoa (+ 1 (atoi freti))) "romans" 12 127 (+ 405 (* 18 (1- contci))))
      )
    )
    (setq freti (itoa (+ 2 (atoi freti))))
    (setq contci (1+ contci))
  )
)

(defun atzindice2 (fechaini fechafin indice)
  (setq finidc (itoa (+ (atoi fechaini) (* 20 (1- (atoi indice))))))
  (if (< (atoi finidc) (atoi fechafin))
    (progn
;      (fill_image 3 270 173 252 0)
;      (slide_image 3 270 173 252 (STRCAT RUTA "SLIDES\\INDICE.SLD"))
      (setq nciclos (1+ (/ (- (atoi fechafin) (atoi fechaini)) 20)))
      (if (>= nciclos (atoi indice))
        (progn
          (setq contci 1)
          (repeat 12
            (fill_image 9 (+ 405 (fix (* 17.8 (1- contci)))) 62 13 252)
            (setq contci (1+ contci))
          )
        )
      )
      (setq contci 1)
      (setq freti fechaini)
  (repeat nciclos
    (if (= contci (atoi indice))
      (progn
        (fill_image 9 (+ 405 (* 18 (1- contci))) 62 13 21)
        (if (= nciclos 1)
          (stexto (strcat freti "-" fechafin) "romans" 12 8 (+ 405 (* 18 (1- contci))))
          (if (= nciclos contci)
            (stexto (strcat freti "-" fechafin) "romans" 12 8 (+ 405 (* 18 (1- contci))))
            (stexto (strcat freti "-" (itoa (+ 19 (atoi freti)))) "romans" 12 8 (+ 405 (* 18 (1- contci))))
          )
        )
      )
      (if (/= nciclos contci)
        (stexto (strcat freti "-" (itoa (+ 19 (atoi freti)))) "romans" 12 8 (+ 405 (* 18 (1- contci))))
        (stexto (strcat freti "-" fechafin) "romans" 12 8 (+ 405 (* 18 (1- contci))))
      )
    )
    (setq freti (itoa (+ 20 (atoi freti))))
    (setq contci (1+ contci))
  )
      (dibujaindiceb2 finidc fechafin)
    )
  )
)
