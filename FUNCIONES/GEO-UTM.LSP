(DEFUN GEO-UTM (COORDENADA)
  (SETQ EXENTRICIDAD 0.081819191)
  (SETQ EXENTRICIDAD2 0.082094438)
  (SETQ EXENTRICIDAD22 0.006739497)
  (SETQ C 6399593.626)
  (SETQ APLASTAMIENTO 0.0033528107)
  (if (= (type (CAR COORDENADA)) 'STR)
    (SETQ LONGITUD (ATOF (CAR COORDENADA)))
    (SETQ LONGITUD (ATOF (RTOS (CAR COORDENADA) 2 12)))
  )
  (if (= (type (CAdR COORDENADA)) 'STR)
    (SETQ LATITUD (ATOF (CADR COORDENADA)))
    (SETQ LATITUD (ATOF (RTOS (CADR COORDENADA) 2 12)))
  )
  (SETQ LONGITUDR (/ (* LONGITUD 3.14159265359) 180.0000000))
  (SETQ FI (/ (* LATITUD 3.14159265359) 180.000000000))
  (SETQ HUSO (FIX (+ (/ LONGITUD 6) 31)))
  (SETQ MERIDIANOHUSO (- (* HUSO 6) 183))
  (SETQ DELTALAMBDA (- LONGITUDR (/ (* 3.14159265359 MERIDIANOHUSO) 180.000000000)))
  (SETQ COSENOFI (COS FI))
  (SETQ COSENOFI2 (EXPT (COS FI) 2.00000000))
  (SETQ A (* COSENOFI (SIN DELTALAMBDA)))
  (SETQ ZETA (* (/ 1.00000 2.00000) (LOG (ABS (/ (1+ A) (1- A))))))
  (SETQ N (- (ATAN (/ (TAN FI) (COS DELTALAMBDA))) FI))
  (SETQ V (* (/ C (sqrt (1+ (* EXENTRICIDAD22 COSENOFI2)))) 0.9996000000))
  (SETQ XI (* (/ (EXPT EXENTRICIDAD 2) 2) (EXPT ZETA 2) COSENOFI2))
  (SETQ A1 (SIN (* 2.000000 FI)))
  (SETQ A2 (* A1 COSENOFI2))
  (SETQ J2 (+ FI (/ A1 2.000000)))
  (SETQ J4 (/ (+ (* 3.000000 J2) A2) 4.000000))
  (SETQ J6 (/ (+ (* 5.00000 J4) (* A2 COSENOFI2)) 3.000000))
  (SETQ ALPHA (* (/ 3.00000000 4.00000000) EXENTRICIDAD22))
  (SETQ BETA (* (/ 5.00000000 3.00000000) (EXPT ALPHA 2)))
  (SETQ GAMA (* (/ 35.00000000 27.00000000) (EXPT ALPHA 3.000000)))
  (SETQ BCERO (* 0.99960000 C (+ FI (* -1.0000000 ALPHA J2) (* BETA J4) (* -1.0000000 GAMA J6))))
  (SETQ X (+ (* ZETA V (+ 1.00000000 (/ XI 3))) 500000.000000))
  (SETQ Y (+ (* N V (+ 1.00000000 XI)) BCERO))
  (SETQ PUNTOFINAL (LIST X Y))
)

(defun tan (z / cosz)
  (if (zerop (setq cosz (cos z)))
    *INF*    
    (/ (sin z) cosz)
  )
)
