(DEFUN greport (tipor estacion procedencia variable tipodat tipoproceso)
  (desactiva3 "PR1")
  (desactiva3 "PR2")
  (desactiva3 "PR3")
  (desactiva3 "DATOSF1")
  (desactiva3 "DATOSF2")
  (desactiva3 "DATOSF3")
  (desactiva3 "DATOSF4")
  (desactiva3 "DATOSF5")
  (desactiva2 "mapa")
  (desactiva3 "SEL1")
  (fill_image 195 135 468 30 105)
  (fill_image 195 165 468 294 31)  
          (if (AND (OR (= variable 1) (= variable 3)) (OR (= tipoproceso "MA") (= tipoproceso "MI") (= tipoproceso "ME")))
            (SETQ CARY 6)
          )
          (if (AND (OR (= variable 7) (= variable 8) (= variable 9)) (OR (= tipoproceso "MA") (= tipoproceso "MI") (= tipoproceso "ME")) )
            (SETQ CARY 5)
          )
          (if (= tipoproceso "TO")
            (SETQ CARY 9)
          )
          (if (= tipoproceso "VC")
            (SETQ CARY 5)
          )
          (if (and (or (= variable 2) (= variable 4) (= variable 5) (= variable 6)) (/= tipoproceso "VC"))
            (SETQ CARY 1)
          )
  (if (= tipor 4)
    (progn
      (activa2 "CREPORTE2")
      (setq slidexx "RPT(R1)")
      (slide_image 195 135 468 324 (STRCAT RUTA "SLIDES\\" slidexx ".SLD"))
      (pruebasec (leebd estacion procedencia variable "190001" tipodat tipoproceso) carx cary)
      (setq varRec reportelist2)
      (stextoj (cdr (assoc 1 varRec)) "romans" 18 630 256 "D")
      (stextoj (cdr (assoc 2 varRec)) "romans" 18 630 276 "D")
      (stextoj (cdr (assoc 3 varRec)) "romans" 18 630 296 "D")
      (stextoj (substr (cdr (assoc 4 varRec)) 1 24) "romans" 18 630 316 "D")
      (stextoj (substr (cdr (assoc 5 varRec)) 1 40) "romans" 18 245 351 "C")
      (if (> (strlen (cdr (assoc 5 varRec))) 40)
        (stextoj (substr (cdr (assoc 5 varRec)) 41 40) "romans" 18 245 371 "C")
      )
      (if (> (strlen (cdr (assoc 5 varRec))) 80)
        (stextoj (substr (cdr (assoc 5 varRec)) 81 40) "romans" 18 245 391 "C")
      )
    )
  )
  (if (= tipor 5)
    (progn
      (activa2 "CREPORTE2")
      (setq slidexx "RPT(R2)")
      (slide_image 195 135 468 324 (STRCAT RUTA "SLIDES\\" slidexx ".SLD"))
      (testhl (leebd estacion procedencia variable "190001" tipodat tipoproceso) carx cary)
      (setq varRec reportelist2)
      (stextoj (cdr (assoc 1 varRec)) "romans" 18 630 256 "D")
      (stextoj (cdr (assoc 2 varRec)) "romans" 18 630 276 "D")
      (stextoj (cdr (assoc 3 varRec)) "romans" 18 630 296 "D")
      (stextoj (substr (cdr (assoc 4 varRec)) 1 24) "romans" 18 630 316 "D")
      (stextoj (substr (cdr (assoc 5 varRec)) 1 41) "romans" 18 245 351 "C")
      (if (> (strlen (cdr (assoc 5 varRec))) 41)
        (stextoj (substr (cdr (assoc 5 varRec)) 42 41) "romans" 18 245 371 "C")
      )
      (if (> (strlen (cdr (assoc 5 varRec))) 82)
        (stextoj (substr (cdr (assoc 5 varRec)) 83 41) "romans" 18 245 391 "C")
      )
    )
  )
  (if (= tipor 6)
    (progn
      (activa2 "CREPORTE")
      (setq slidexx "RPT(R3)")
      (slide_image 195 135 468 324 (STRCAT RUTA "SLIDES\\" slidexx ".SLD"))
    )
  )
  (if (= tipor 7)
    (progn
      (activa2 "CREPORTE")
      (setq slidexx "RPT(R4)")
      (slide_image 195 135 468 324 (STRCAT RUTA "SLIDES\\" slidexx ".SLD"))
      (persistand estacion procedencia variable "19001" tipodat tipoproceso)
      (setq varRec reportelist2)
      (stextoj (itoa (cdr (assoc 1 varRec))) "romans" 18 630 256 "D")
      (stextoj (substr (cdr (assoc 4 varRec)) 1 24) "romans" 18 630 316 "D")
      (stextoj (substr (cdr (assoc 5 varRec)) 1 40) "romans" 18 245 351 "C")
      (if (> (strlen (cdr (assoc 5 varRec))) 40)
        (stextoj (substr (cdr (assoc 5 varRec)) 41 40) "romans" 18 245 371 "C")
      )
      (if (> (strlen (cdr (assoc 5 varRec))) 80)
        (stextoj (substr (cdr (assoc 5 varRec)) 81 40) "romans" 18 245 391 "C")
      )
    )
  )
  (if (= tipor 8)
    (progn
      (activa2 "CREPORTE")
      (setq slidexx "RPT(R5)")
      (slide_image 195 135 468 324 (STRCAT RUTA "SLIDES\\" slidexx ".SLD"))
    )
  )
  (if (= tipor 9)
    (progn
      (activa2 "CREPORTE")
      (setq slidexx "RPT(R6)")
      (slide_image 195 135 468 324 (STRCAT RUTA "SLIDES\\" slidexx ".SLD"))
    )
  )
  (SETQ OBJETO (BUSOBJBD LISTADCLOBJ 74 "EXCEL11"))
  (dibujaelem OBJETO)
  (SETQ OBJETO (BUSOBJBD LISTADCLOBJ 74 "SALIR11"))
  (dibujaelem OBJETO)
  (SETQ OBJETO (BUSOBJBD LISTADCLOBJ 74 "GRAFICA11"))
  (IF (/= OBJETO "")
    (dibujaelem OBJETO)
  )
)

(defun reporteprsec (cadenacorrela archivoesc)
  (setq nestaccx (/ (strlen cadenacorrela) 6))
  (setq cont1 1)
  (setq archivo (open archivoesc "w"))
  (repeat nestaccx
    (SETQ lineaex (SUBSTR cadenacorrela (1+ (* (1- CONT1) 6)) 6))
    (setq bdextraida (leebd (substr lineaex 1 5) (substr lineaex 6 1) 3 "190001" "AN" "MA"))
    (if (/= bdextraida "")
      (pruebasec bdextraida carx cary)
    )
    (setq varRec reportelist2)
    (SETQ lineaex (strcat lineaex (cdr (assoc 5 varRec))))
    (WRITE-LINE LINEAex ARCHIvo)    
    (SETQ CONT1 (1+ CONT1))
  )
  (close archivo)
)

(defun reporteHEL (cadenacorrela archivoesc)
  (setq nestaccx (/ (strlen cadenacorrela) 6))
  (setq cont1 1)
  (setq archivo (open archivoesc "w"))
  (repeat nestaccx
    (SETQ lineaex (SUBSTR cadenacorrela (1+ (* (1- CONT1) 6)) 6))
    (setq bdextraida (leebd (substr lineaex 1 5) (substr lineaex 6 1) 3 "190001" "AN" "MA"))
    (if (/= bdextraida "")
      (testhl bdextraida carx cary)
    )
    (setq varRec reportelist2)
    (SETQ lineaex (strcat lineaex (cdr (assoc 5 varRec))))
    (WRITE-LINE LINEAex ARCHIvo)    
    (SETQ CONT1 (1+ CONT1))
  )
  (close archivo)
)

(defun reportePER (cadenacorrela archivoesc)
  (setq nestaccx (/ (strlen cadenacorrela) 6))
  (setq cont1 1)
  (setq archivo (open archivoesc "w"))
  (repeat nestaccx
    (SETQ lineaex (SUBSTR cadenacorrela (1+ (* (1- CONT1) 6)) 6))
    (setq bdextraida (leebd (substr lineaex 1 5) (substr lineaex 6 1) 3 "190001" "AN" "MA"))
    (if (/= bdextraida "")
      (persistand (substr lineaex 1 5) (substr lineaex 6 1) 3 "190001" "AN" "MA")
    )
    (setq varRec reportelist2)
    (SETQ lineaex (strcat lineaex (cdr (assoc 5 varRec))))
    (WRITE-LINE LINEAex ARCHIvo)    
    (SETQ CONT1 (1+ CONT1))
  )
  (close archivo)
)


(defun desactiva3 (EVENTOX)
  (SETQ OBJETO (BUSOBJBD LISTADCLOBJ 74 EVENTOX))
  (SETQ OBJETO2 (BUSOBJBD LISTADCLOBJ2 274 EVENTOX))
  (if (/= objeto "")
    (SETQ LISTADCLOBJ (ACTUALIZABD LISTADCLOBJ 74 EVENTOX (strcat (substr OBJETO 1 31) "2" (substr OBJETO 33))))
    (SETQ LISTADCLOBJ2 (ACTUALIZABD LISTADCLOBJ2 274 EVENTOX (strcat (substr OBJETO2 1 31) "2" (substr OBJETO2 33))))
  )
)

(defun activa3 (EVENTOX)
  (SETQ OBJETO (BUSOBJBD LISTADCLOBJ 74 EVENTOX))
  (SETQ OBJETO2 (BUSOBJBD LISTADCLOBJ2 274 EVENTOX))
  (if (/= objeto "")
    (SETQ LISTADCLOBJ (ACTUALIZABD LISTADCLOBJ 74 EVENTOX (strcat (substr OBJETO 1 31) "0" (substr OBJETO 33))))
    (SETQ LISTADCLOBJ2 (ACTUALIZABD LISTADCLOBJ2 274 EVENTOX (strcat (substr OBJETO2 1 31) "0" (substr OBJETO2 33))))
  )
)

;(reporteprsec "16001C16010C16022C16049C16055C16062C16087C16109C16114C16120C16123C16133C16136C16139C16140C16146C16168C16187C16193C16230C16247C16257C16512C16513C16001E16010E16022E16049E16055E16062E16087E16109E16114E16120E16123E16133E16136E16139E16140E16146E16168E16187E16193E" "C:\\descarga.txt")
;(reporteHEL "16001C16010C16022C16049C16055C16062C16087C16109C16114C16120C16123C16133C16136C16139C16140C16146C16168C16187C16193C16230C16247C16257C16512C16513C16001E16010E16022E16049E16055E16062E16087E16109E16114E16120E16123E16133E16136E16139E16140E16146E16168E16187E16193E" "C:\\descarga.txt")
;(reportePER "16001C16010C16022C16049C16055C16062C16087C16109C16114C16120C16123C16133C16136C16139C16140C16146C16168C16187C16193C16230C16247C16257C16512C16513C16001E16010E16022E16049E16055E16062E16087E16109E16114E16120E16123E16133E16136E16139E16140E16146E16168E16187E16193E" "C:\\descarga.txt")
;(Lista->Excel (leebdex "16109" (SUBSTR procedencia 1 1) DATOSFT2 DATOSFT1 DATOSFT3))
