(DEFUN BUSACC2 (LISTAOBJD COORDX COORDY anchol)
  (SETQ ACCIONE "")
  (SETQ CONTBUS 0)
  (WHILE (= ACCIONE "")
    (SETQ X1 (ATOI (SUBSTR LISTAOBJD (1+ (* CONTBUS anchol)) 4)))
    (SETQ Y1 (ATOI (SUBSTR LISTAOBJD (+ 5 (* CONTBUS anchol)) 4)))
    (SETQ X2 (ATOI (SUBSTR LISTAOBJD (+ 9 (* CONTBUS anchol)) 4)))
    (SETQ Y2 (ATOI (SUBSTR LISTAOBJD (+ 13 (* CONTBUS anchol)) 4)))
    (SETQ ACCIONX (SUBSTR LISTAOBJD (+ 17 (* CONTBUS anchol)) 14))
    (IF (AND (< X1 COORDX) (> X2 COORDX) (< Y1 COORDY) (> Y2 COORDY)) (SETQ ACCIONE ACCIONX))
    (if (/= ACCIONE "")
      (progn
        (setq tipoobj (SUBSTR LISTAOBJD (+ 31 (* CONTBUS anchol)) 1))
        (if (or (= tipoobj "B") (= tipoobj "C") (= tipoobj "D") (= tipoobj "H") (= tipoobj "F") (= tipoobj "G"))
          (progn
            (setq statusobj (SUBSTR LISTAOBJD (+ 32 (* CONTBUS anchol)) 1))
            (if (/= statusobj "2")
              (progn
                (if (= tipoobj "F")
                  (progn
                    (if (= statusobj "0") (setq LISTADCLOBJ (strcat (substr LISTADCLOBJ 1 (+ 31 (* CONTBUS anchol))) "1" (substr LISTADCLOBJ (+ 33 (* CONTBUS anchol))))))
                    (if (= statusobj "1") (setq LISTADCLOBJ (strcat (substr LISTADCLOBJ 1 (+ 31 (* CONTBUS anchol))) "0" (substr LISTADCLOBJ (+ 33 (* CONTBUS anchol))))))
                    (setq elemdb (substr LISTADCLOBJ (1+ (* CONTBUS anchol)) anchol))
                    (dibujaelem elemdb)
                  )
                )
                (if (OR (= tipoobj "B") (= tipoobj "G"))
                  (progn
                    (if (= statusobj "0") (setq LISTADCLOBJ (strcat (substr LISTADCLOBJ 1 (+ 31 (* CONTBUS anchol))) "1" (substr LISTADCLOBJ (+ 33 (* CONTBUS anchol))))))
                    (if (= statusobj "1") (setq LISTADCLOBJ (strcat (substr LISTADCLOBJ 1 (+ 31 (* CONTBUS anchol))) "0" (substr LISTADCLOBJ (+ 33 (* CONTBUS anchol))))))
                    (setq elemdb (substr LISTADCLOBJ (1+ (* CONTBUS anchol)) anchol))
                    (dibujaelem elemdb)
                  )
                )
                (if (= tipoobj "C")
                  (progn
                    (SETQ listaobjf (SUBSTR LISTAOBJD (1+ (* CONTBUS anchol)) anchol))
                    (setq cadenaproc (substr listaobjf 95 160))
                    (setq ancho (atoi (substr listaobjf 89 3)))
                    (setq alto (atoi (substr listaobjf 92 3)))
                    (setq vespecifico (buscaesp cadenaproc alto ancho))
                    (if (/= vespecifico "")
                      (progn
                        (setq activop (substr listaobjf (+ 254 vespecifico) 1))
                        (if (/= activop "1")
                          (progn
                            (setq cadenaSTATS (substr listaobjf 255 20))
                            (SETQ SAL "")
                            (SETQ CONTSALDLG 1)
                            (WHILE (AND (= SAL "") (<= CONTSALDLG 20))
                              (IF (= (SUBSTR cadenaSTATS CONTSALDLG 1) "1") 
                                (PROGN
                                  (dibujaop3 (vl-string-trim " " (SUBSTR listaobjf 95 160)) "00000000000000000000" CONTSALDLG (vl-string-trim " " (SUBSTR listaobjf 33 14)) (vl-string-trim " " (SUBSTR listaobjf 47 14)) (vl-string-trim " " (SUBSTR listaobjf 61 14)))
                                  (SETQ SAL "S")
                                )
                              )
                              (SETQ CONTSALDLG (1+ CONTSALDLG))
                            )
                            (setq cadenastop "00000000000000000000");(ATOI "10000000000000000000")
                            (setq cadenastop (strcat (substr cadenastop 1 (1- vespecifico)) "1" (substr cadenastop (1+ vespecifico))))
                            (setq LISTADCLOBJ2 (strcat (substr LISTADCLOBJ2 1 (+ 254 (* CONTBUS anchol))) cadenastop (substr LISTADCLOBJ2 (1+ (* (1+ CONTBUS) anchol)))))
                            (setq elemdb (substr LISTADCLOBJ2 (1+ (* CONTBUS anchol)) anchol))
                            (dibujaop3 (vl-string-trim " " (SUBSTR ELEMDB 95 160)) (SUBSTR ELEMDB 255 20) vespecifico (vl-string-trim " " (SUBSTR ELEMDB 33 14)) (vl-string-trim " " (SUBSTR ELEMDB 47 14)) (vl-string-trim " " (SUBSTR ELEMDB 61 14)))
                            (SETQ ACCIONE (strcat ACCIONE "-" (itoa vespecifico)))
                          )
                          (SETQ ACCIONE (strcat ACCIONE "-" (itoa vespecifico)))
                        )
                      )
                      (SETQ ACCIONE "")
                    )
                  )
                );if
                (if (OR (= tipoobj "D") (= tipoobj "H"))
                  (progn
                    (SETQ listaobjf (SUBSTR LISTAOBJD (1+ (* CONTBUS anchol)) anchol))
                    (setq cadenaproc (substr listaobjf 95 160))
                    (setq ancho (atoi (substr listaobjf 89 3)))
                    (setq alto (atoi (substr listaobjf 92 3)))
                    (setq vespecifico (buscaesp cadenaproc alto ancho))
                    (if (/= vespecifico "")
                      (progn
                        (setq activop (substr listaobjf (+ 254 vespecifico) 1))
                        (if (/= activop "1")
                          (progn
                            (setq cadenastop (substr listaobjf 255 20))
                            (setq cadenastop (strcat (substr cadenastop 1 (1- vespecifico)) "1" (substr cadenastop (1+ vespecifico))))
                            (setq LISTADCLOBJ2 (strcat (substr LISTADCLOBJ2 1 (+ 254 (* CONTBUS anchol))) cadenastop (substr LISTADCLOBJ2 (1+ (* (1+ CONTBUS) anchol)))))
                            (setq elemdb (substr LISTADCLOBJ2 (1+ (* CONTBUS anchol)) anchol))
                            (dibujaop3 (vl-string-trim " " (SUBSTR ELEMDB 95 160)) (SUBSTR ELEMDB 255 20) vespecifico (vl-string-trim " " (SUBSTR ELEMDB 33 14)) (vl-string-trim " " (SUBSTR ELEMDB 47 14)) (vl-string-trim " " (SUBSTR ELEMDB 61 14)))
                            (SETQ ACCIONE (strcat ACCIONE "-" (itoa vespecifico)))
                          )
                          (progn
                            (setq cadenastop (substr listaobjf 255 20))
                            (setq cadenastop (strcat (substr cadenastop 1 (1- vespecifico)) "0" (substr cadenastop (1+ vespecifico))))
                            (setq LISTADCLOBJ2 (strcat (substr LISTADCLOBJ2 1 (+ 254 (* CONTBUS anchol))) cadenastop (substr LISTADCLOBJ2 (1+ (* (1+ CONTBUS) anchol)))))
                            (setq elemdb (substr LISTADCLOBJ2 (1+ (* CONTBUS anchol)) anchol))
                            (dibujaop3 (vl-string-trim " " (SUBSTR ELEMDB 95 160)) (SUBSTR ELEMDB 255 20) vespecifico (vl-string-trim " " (SUBSTR ELEMDB 33 14)) (vl-string-trim " " (SUBSTR ELEMDB 47 14)) (vl-string-trim " " (SUBSTR ELEMDB 61 14)))
                            (SETQ ACCIONE (strcat ACCIONE "-" (itoa vespecifico)))
                          )
                        )
                      )
                      (SETQ ACCIONE "")
                    )
                  )
                );if
              )
              (SETQ ACCIONE "")
            )
          )
        )
      )
    )
    (SETQ CONTBUS (1+ CONTBUS))
    (IF (> (* CONTBUS anchol) (STRLEN LISTAOBJD)) (SETQ ACCIONE NIL))
  )
  (IF (/= ACCIONE NIL)
    (SETQ ACCIONE (vl-string-trim " " ACCIONE))
    (SETQ ACCIONE "SIN OBJETO")
  )
)

(defun buscaesp (cadenaproc altoe anchoe)
  (setq nobj (/ (strlen cadenaproc) 8))
  (setq contesp 0)
  (setq respuesta "")
  (while (and (= respuesta "") (<= contesp nobj))
    (setq elemnto (substr cadenaproc (1+ (* contesp 8)) 8))
    (IF (AND (< (atoi (substr elemnto 1 4)) COORDX) (> (+ (atoi (substr elemnto 1 4)) anchoe) COORDX) (< (atoi (substr elemnto 5 4)) COORDY) (> (+ (atoi (substr elemnto 5 4)) altoe) COORDY)) (SETQ respuesta (1+ contesp)))
    (setq contesp (1+ contesp))
  )
  (setq respuesta respuesta)
)


;LISTAOBJD	CADENA		LISTA DE DATOS DE CADENA CON NOMBRE DE LA ACCION ENCONTRADA Y CON DATOS DE COORDENADAS DE LAS ESQUINAS DE LOS OBJETOS EN EL BOTON
;COORX		ENTERO		DATO ENTERO DE LA COORDENADA PULSADA POR EL USUARIO
;COORY		ENTERO		DATO ENTERO DE LA COORDENADA PULSADA POR EL USUARIO
;anchol		entero		ancho de la linea de datos
