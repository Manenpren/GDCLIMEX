(DEFUN S_OBJ_GPO (GPO NINICIO NASOCIAB ASOCIACIONB OBR)
  (SETQ OBR 0)
  (SETQ OBJ (SSNAME GPOA OBR))
  (WHILE (AND (/= OBJ NIL) (= OBR 0))
    (IF (= (cdr (assoc NASOCIAB (entget OBJ))) ASOCIACIONB)  
      (SETQ OBR NINICIO)
    )
    (SETQ INICIO (1+ INICIO))
    (SETQ OBJ (SSNAME GPOA OBR))
  )
)
