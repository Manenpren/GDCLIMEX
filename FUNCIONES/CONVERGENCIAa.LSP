(DEFUN CONVERGENCIAa (PUNTOU ZONAHORARIA)
  (C:LIBRERIA "UTM-GEO")
  (C:LIBRERIA "GEO-UTM")
  (C:LIBRERIA "DECIMALTOSEXAGESIMAL")
  (SETQ PUNTOGEOGRAFICO (UTM-GEO PUNTOU ZONAHORARIA))
  (SETQ LATITUDREF (ATOF (RTOS (CAR puntoGEOGRAFICO) 2 15)))
  (SETQ LONGITUDREF (ATOF (RTOS (CADR puntoGEOGRAFICO) 2 15)))
  (SETQ PUNTOGEOGRAFICO2 (LIST LATITUDREF (+ LONGITUDREF 0.01000000000)))
  (SETQ XYZCONVERGENCIA (GEO-UTM PUNTOGEOGRAFICO2))
  (SETQ CONVERGENCIA (ATOF (RTOS (ANGLE PUNTOU XYZCONVERGENCIA) 2 12)))
  (SETQ CONVERGENCIA (- (/ (* CONVERGENCIA 180.00000) 3.14159265359) 90.0000000000))
  (SETQ CONVERGENCIA (DECSEXA CONVERGENCIA))
)
