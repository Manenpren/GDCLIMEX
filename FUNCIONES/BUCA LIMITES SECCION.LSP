(DEFUN BLIMSEC (ZOOMB)
  (C:LIBRERIA "VERTICES DE UNA LWPOLYLINE")
  (SETQ X (ENTLAST))
  (COMMAND "EXPLODE" X)
  (SETQ GPOA (SSGET "P"))
    (SETQ PROV (SSNAME GPOA 0))
    (SETQ AO (ENTGET PROV))
    (SETQ PUNTO (cdr (assoc 10 AO)))
    (SETQ BX (CAR PUNTO))
    (SETQ BY (CADR PUNTO))
    (SETQ XDMAX BX)
    (SETQ XIMAX BX) 
    (SETQ YUMAX BY)
    (SETQ YDMAX BY)
  (SETQ P2 0)  
  (SETQ PROV (SSNAME GPOA P2))
  (SETQ AO (ENTGET PROV))
  (WHILE (/= PROV NIL)
;    (IF (OR (AND (= (cdr (assoc 0 AO)) "LINE") (= (cdr (assoc 8 AO)) "LOTIFICACION")) (AND (= (cdr (assoc 0 AO)) "LINE") (= (cdr (assoc 8 AO)) "0")))                       ;LINEA
;       (COMMAND "ERASE" PROV "")
;    )
;    (IF (AND (or (= (cdr (assoc 0 AO)) "LINE") (= (cdr (assoc 0 AO)) "TEXT")) (= (cdr (assoc 8 AO)) "PROYECTO"))                        ;LINEA
;       (COMMAND "ERASE" PROV "")
;    )
;    (IF (AND (or (= (cdr (assoc 0 AO)) "LINE") (= (cdr (assoc 0 AO)) "TEXT")) (= (cdr (assoc 8 AO)) "PR"))                        ;LINEA
;       (COMMAND "ERASE" PROV "")
;    )
;    (IF (= (cdr (assoc 2 AO)) "A-ARBOL3")                        ;LINEA
;       (COMMAND "ERASE" PROV "")
;    )
;    (IF (= (cdr (assoc 0 AO)) "INSERT")                        ;LINEA
;       (COMMAND "ERASE" PROV "")
;    )
;    (IF (= (cdr (assoc 2 AO)) "A-ARBOL3")                        ;LINEA
;       (COMMAND "ERASE" PROV "")
;    )
;    (IF (OR (= (cdr (assoc 1 AO)) "Pend. 1%") (= (cdr (assoc 1 AO)) "Rs+") (= (cdr (assoc 1 AO)) "Pend. 2%"))                       ;LINEA;
;       (COMMAND "ERASE" PROV "")
;    )
;    (IF (= (cdr (assoc 0 AO)) "LINE")                         ;LINEA
;      (PROGN
;        (SETQ PUNTO (cdr (assoc 10 AO)))
;        (SETQ BX (CAR PUNTO))
;        (SETQ BY (CADR PUNTO))
;        (SETQ PUNTO2 (cdr (assoc 11 AO)))
;        (SETQ BX2 (CAR PUNTO2))
;        (SETQ BY2 (CADR PUNTO2))
;        (if (or (= BX BX2) (= BY BY2)) (COMMAND "CHANGE" PROV "" "P" "LA" "RETICULA" ""))
;      )
;    )
    (IF (AND (= (cdr (assoc 0 AO)) "LWPOLYLINE") (= (cdr (assoc 8 AO)) "TN"))                        ;LINEA
      (SETQ POLTN PROV)
    )
    (IF (AND (= (cdr (assoc 0 AO)) "LWPOLYLINE") (= (cdr (assoc 8 AO)) "TN") (= (cdr (assoc 62 AO)) 1))                        ;LINEA
      (SETQ POLTN2 PROV)
    )
    (IF (= (cdr (assoc 0 AO)) "TEXT")                             ;TEXTO
      (PROGN
        (SETQ NOMBRE (cdr (assoc 1 AO)))
        (SETQ LNG (STRLEN NOMBRE))
        (SETQ PUNTO (cdr (assoc 11 AO)))
        (SETQ BX (CAR PUNTO))
        (SETQ BY (CADR PUNTO))
        (SETQ ESCALA (cdr (assoc 40 AO)))
        (SETQ JUSTIFICACION (cdr (assoc 72 AO)))
        (SETQ JUSTIFICACION2 (cdr (assoc 62 AO)))
        (IF (AND (= JUSTIFICACION2 6) (= JUSTIFICACION 1))
          (PROGN
            (SETQ BX2 (+ BX (/ (* ESCALA LNG) 2)))
            (SETQ BY2 (- BY (/ ESCALA 2)))
            (SETQ BX (- BX (/ (* ESCALA LNG) 2)))
            (SETQ BY (+ BY (/ ESCALA 2)))
          )
        )
        (IF (AND (/= JUSTIFICACION2 6) (= JUSTIFICACION 1))
          (PROGN
            (SETQ BX2 (+ BX (/ (* ESCALA LNG) 2)))
            (SETQ BY2 BY)
            (SETQ BX (- BX (/ (* ESCALA LNG) 2)))
            (SETQ BY (+ BY ESCALA))
          )
        )
        (IF (AND (= JUSTIFICACION2 6) (= JUSTIFICACION 0))
          (PROGN
            (SETQ BX2 (+ BX (* ESCALA LNG)))
            (SETQ BY2 (- BY (/ ESCALA 2)))
            (SETQ BY (+ BY (/ ESCALA 2)))
          )
        )
        (IF (AND (= JUSTIFICACION2 6) (= JUSTIFICACION 2))
          (PROGN
            (SETQ BX2 BX)
            (SETQ BY2 (- BY (/ ESCALA 2)))
            (SETQ BX (- BX (* ESCALA LNG)))
            (SETQ BY (+ BY (/ ESCALA 2)))
          )
        )
      ) 
    )
    (IF (= (cdr (assoc 0 AO)) "LWPOLYLINE")                             ;PLINE
      (PROGN
        (setq f 0)
        (SETQ VERY "")
        (while verY
          (setq f (1+ f))
          (SETQ VERY (vertice (cdr (assoc -1 AO)) f)) 
          (IF (/= VERY NIL)
           (PROGN
            (SETQ BX (CAR VERY))
            (SETQ BY (CADR VERY))
            (IF (> BX XDMAX)
              (SETQ XDMAX BX)
            )
            (IF (< BX XIMAX)
              (SETQ XIMAX BX)
            )
            (IF (> BY YUMAX)
              (SETQ YUMAX BY)
            )
            (IF (< BY YDMAX)
              (SETQ YDMAX BY)
            )
            (IF (> BX2 XDMAX)
              (SETQ XDMAX BX2)
            )
            (IF (< BX2 XIMAX)
              (SETQ XIMAX BX2)
            )
            (IF (> BY2 YUMAX)
              (SETQ YUMAX BY2)
            )
            (IF (< BY2 YDMAX)
              (SETQ YDMAX BY2)
            )
           )
          )
        )
      ) 
    )
    (IF (> BX XDMAX)
      (SETQ XDMAX BX)
    )
    (IF (< BX XIMAX)
      (SETQ XIMAX BX)
    )
    (IF (> BY YUMAX)
      (SETQ YUMAX BY)
    )
    (IF (< BY YDMAX)
      (SETQ YDMAX BY)
    )
    (IF (> BX2 XDMAX)
      (SETQ XDMAX BX2)
    )
    (IF (< BX2 XIMAX)
      (SETQ XIMAX BX2)
    )
    (IF (> BY2 YUMAX)
      (SETQ YUMAX BY2)
    )
    (IF (< BY2 YDMAX)
      (SETQ YDMAX BY2)
    )
    (IF (= ximax nil)
      (SETQ ximax bx)
    )
    (IF (= ydmax nil)
      (SETQ ydmax by)
    )
    (SETQ P2 (1+ P2))   
    (SETQ PROV (SSNAME GPOA P2))
    (IF (/= PROV NIL)
       (SETQ AO (ENTGET PROV))
    )
  )
  (SETQ ZOOMB (- BX BX2))
)
