(DEFUN tempdiaria (cadenapr datoclim fechaini)
  (C:LIBRERIA "CONVIERTE NUMERO EN CADENA")
  (if (= datoclim 1) (progn (setq ndec 2) (setq anchochr 6)))
  (if (= datoclim 2) (progn (setq ndec 0) (setq anchochr 1)))
  (if (= datoclim 3) (progn (setq ndec 2) (setq anchochr 6)))
  (if (= datoclim 4) (progn (setq ndec 0) (setq anchochr 1)))
  (if (= datoclim 5) (progn (setq ndec 0) (setq anchochr 1)))
  (if (= datoclim 6) (progn (setq ndec 0) (setq anchochr 1)))
  (if (= datoclim 7) (progn (setq ndec 2) (setq anchochr 5)))
  (if (= datoclim 8) (progn (setq ndec 2) (setq anchochr 5)))
  (if (= datoclim 9) (progn (setq ndec 2) (setq anchochr 5)))
    (setq cadg "")
  (setq anchol (+ 11 (* 31 anchochr)))
  (setq nmeses (/ (strlen cadenapr) anchol))
    (dos_getprogress "Trabajando" "procesando datos diarios" nmeses)
  (setq caracterprov "")
  (repeat anchochr
    (setq caracterprov (strcat caracterprov "x"))
  )
  (setq contci2 1)
  (setq ldat (substr cadenapr (1+ (* anchol (1- contci2))) anchol))
  (if (> (atoi (substr fechaini 1 4)) (atoi (substr ldat 1 4)))
    (progn
      (while (>= (+ (atoi (substr fechaini 1 4)) (/ (atoi (substr fechaini 5 2)) 12)) (+ (atoi (substr ldat 1 4)) (/ (atoi (substr ldat 5 2)) 12)))
        (setq contci2 (1+ contci2))
        (setq ldat (substr cadenapr (1+ (* anchol (1- contci2))) anchol))
      )
    );progn
  )
  (setq cadenaprov "")
  (setq contdias 1)
  (setq contci contci2)
  (setq fret fechaini)
  (setq ldat "x")
  (repeat nmeses
    (setq ldat (substr cadenapr (1+ (* anchol (1- contci))) anchol))
    (if (/= fret (substr ldat 1 6))
      (progn
        (setq fretx (substr ldat 1 6))
        (while (/= fret fretx)
          (if (/= fret fretx)
            (progn
              (setq mes (substr fret 5 2))
              (setq fret (mesmas fret))
              (if (= mes "01") (setq ndias 31))
              (if (= mes "03") (setq ndias 31))
              (if (= mes "04") (setq ndias 30))
              (if (= mes "05") (setq ndias 31))
              (if (= mes "06") (setq ndias 30))
              (if (= mes "07") (setq ndias 31))
              (if (= mes "08") (setq ndias 31))
              (if (= mes "09") (setq ndias 30))
              (if (= mes "10") (setq ndias 31))
              (if (= mes "11") (setq ndias 30))
              (if (= mes "12") (setq ndias 31))
              (if (= mes "02")
                (progn
                  (setq fx (atoi (substr fret 1 4)))
                  (setq dx (* (fix (/ fx 4.0)) 4.0))
                  (if (= dx fx)
                    (setq ndias 29)
                    (setq ndias 28)
                  )
                )
              );if
              ;(print ndias)
              (setq contdias (+ contdias ndias))              
            )
          );if
        )
      )
    )
    (setq amo (substr ldat 1 4))
    (setq mes (substr ldat 5 2))
    (if (= mes "01") (setq ndias 31))
    (if (= mes "03") (setq ndias 31))
    (if (= mes "04") (setq ndias 30))
    (if (= mes "05") (setq ndias 31))
    (if (= mes "06") (setq ndias 30))
    (if (= mes "07") (setq ndias 31))
    (if (= mes "08") (setq ndias 31))
    (if (= mes "09") (setq ndias 30))
    (if (= mes "10") (setq ndias 31))
    (if (= mes "11") (setq ndias 30))
    (if (= mes "12") (setq ndias 31))
    (if (= mes "02")
      (progn
        (setq fx (atoi amo))
        (setq dx (* (fix (/ fx 4.0)) 4.0))
        (if (= dx fx)
          (setq ndias 29)
          (setq ndias 28)
        )
      )
    )
    (setq cadenaprov (strcat cadenaprov (separames ldat ndias)))
    (setq fret (mesmas fret))
    (dos_getprogress contci)
    (setq contci (1+ contci))
  )
  (dos_getprogress t)
  (setq cadenaprov cadenaprov)
)

(defun separames (cadenaf ndias)
  (setq contmx 1)
  (setq vmedio "")
  (repeat ndias
    (setq chrprov (substr cadenaf (+ 7 (* anchochr (1- contmx))) anchochr))
    (if (/= chrprov caracterprov)
      (progn
        (setq vmedio (strcat vmedio (ntocad contdias 0 6) chrprov))
      )
    )
    (setq contmx (1+ contmx))
    (setq contdias (1+ contdias))
  )
  (setq vmedio vmedio)
)

(defun mesmas (fecha)
  (setq mes (substr fecha 5 2))
  (if (= mes "12")
    (progn
      (setq amo (1+ (atoi (substr fecha 1 4))))
      (setq fechaf (strcat (itoa amo) "01"))
    )
    (progn
      (setq fechaf (strcat (substr fecha 1 4) (NTOCAD (1+ (atoi (substr fecha 5 2))) 0 2)))
    )
  )
  (setq fechaf fechaf)
)

(defun anmas (fecha)
  (setq fechaf (itoa (1+ (atoi fecha))))
)

;cadenapr	cadena		cadena fuente a procesar
;datoclim	entero		numero de dato climatologico a procesar
;fechaini	cadena		fecha de comienzo de los datos "198101"

;  (setq ArcCon (open "d:\\x.cli" "r"))
;  (setq lINEAfUENTE (read-line arcCon))
;  (close arcCon)
;  (setq prov (tempdiaria lineafuente 1 "198712"))
;  (prommov "0001000000008000200000000300030000000050004000000008000500000000200060000000080007000000008000800000000500090000000040010000000008")
