(DEFUN stexto (textoesr xfuente xtamaño xins yins)
  (if (= nil Ddespfuente) 
    (progn
      (setq archIVOCL (open (strcat ruta "fuentes\\" xfuente ".fnt") "r"))
      (IF (= ARCHIVOCL NIL) (exit))
      (setq lINEAfUENTE (read-line archIVOCL))
      (setq CONCATENADO (cons -1 xfuente)) 
      (setq Ddespfuente (append Ddespfuente (list CONCATENADO)))
      (setq CONCATENADO (cons 0 (atoi lineafuente))) 
      (setq Ddespfuente (append Ddespfuente (list CONCATENADO)))
      (setq xcont1 1)
      (repeat 255
        (setq lINEAfUENTE (read-line archIVOCL))
        (setq CONCATENADO (cons xcont1 (atoi lineafuente))) 
        (setq Ddespfuente (append Ddespfuente (list CONCATENADO)))
        (setq xcont1 (1+ xcont1))
      )
      (close archivocl)
    )
    (progn
      (setq cfnt (cdr (assoc -1 Ddespfuente)))
      (if (/= cfnt xfuente)
        (progn
          (setq archIVOCL (open (strcat ruta "fuentes\\" xfuente ".fnt") "r"))
          (IF (= ARCHIVOCL NIL) (END))
          (setq lINEAfUENTE (read-line archIVOCL))
          (setq CONCATENADO (cons -1 xfuente)) 
          (setq Ddespfuente (append Ddespfuente (list CONCATENADO)))
          (setq CONCATENADO (cons 0 (atoi lineafuente))) 
          (setq Ddespfuente (append Ddespfuente (list CONCATENADO)))
          (setq xcont1 1)
          (repeat 255
            (setq lINEAfUENTE (read-line archIVOCL))
            (setq CONCATENADO (cons xcont1 (atoi lineafuente))) 
            (setq Ddespfuente (append Ddespfuente (list CONCATENADO)))
            (setq xcont1 (1+ xcont1))
          )
          (close archivocl)
        )
      )
    )
  )
  (setq nomfnt (cdr (assoc -1 Ddespfuente)))
  (setq hfuentex (cdr (assoc 0 Ddespfuente)))
  (setq proporcion (/ (+ xtamaño 0.00001) (+ hfuentex 0.00001)))
  (SETQ LNGcad (STRLEN textoesr))
  (setq xcont1 1)
  (repeat lngcad
     (SETQ Ptext (SUBSTR textoesr xcont1 1))
     (setq espacioc (atoi (rtos (* proporcion (cdr (assoc (ascii ptext) Ddespfuente))) 2 0)))
     (slide_image xins yins espacioc xtamaño (STRCAT RUTA "fuentes\\" xfuente "(L" (itoa (ascii ptext)) ")"))
     (setq xins (+ xins espacioc))
     (setq xcont1 (1+ xcont1))
  )
); (stexto "textoesr" "euroman" xtamaño xins yins)
