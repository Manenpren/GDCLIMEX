(DEFUN testcram (lista1 lista2 carx cary)
  (C:LIBRERIA "media ar")
  (C:LIBRERIA "calculo s cuadrada")
  (C:LIBRERIA "d grados de libertad")
  (setq n1 (/ (strlen lista1) (+ carx cary)))
  (setq n2 (/ (strlen lista2) (+ carx cary)))
  (setq listaxc (strcat lista1 lista2))
  (setq mediaxc (mediaar listaxc carx cary))
  (setq media1 (mediaar lista1 carx cary))
  (setq media2 (mediaar lista2 carx cary))
  (setq sx (sqrt (scuad listaxc carx cary)))
  (setq u (+ n1 n2 -2))
  (setq d (dgradosl u))
  (setq d1 (atof (substr d 1 5)))
  (setq d2 (atof (substr d 6 6)))
  (setq reportelist2 NIL)
  (setq CONCATENADO (cons 1 (itoa n1)))
  (setq reportelist2 (append reportelist2 (list CONCATENADO)))
  (setq CONCATENADO (cons 2 (itoa n2)))
  (setq reportelist2 (append reportelist2 (list CONCATENADO)))
  (setq CONCATENADO (cons 3 (rtos sx 2 3)))
  (setq reportelist2 (append reportelist2 (list CONCATENADO)))
  (if (> media1 media2)
    (progn
      (setq nx n1)
      (setq xk media1)
    )
    (progn
      (setq nx n2)
      (setq xk media2)
    )
  )
  (setq tk (/ (- xk mediaxc) sx))
  (setq td (* (expt (/ (* (- (+ n1 n2) 2) nx) (* (- (+ n1 n2) nx) (1+ (expt tk 2)))) (/ 1.00 2.00)) tk))
  (if (<= td d1) (setq resultado "BIEN"))
  (if (> td d1) (setq resultado "ERR"))
  (setq CONCATENADO (cons 4 (rtos tk 2 3)))
  (setq reportelist2 (append reportelist2 (list CONCATENADO)))
  (setq CONCATENADO (cons 5 (rtos td 2 3)))
  (setq reportelist2 (append reportelist2 (list CONCATENADO)))
  (IF (= RESULTADO "BIEN")
    (setq CONCATENADO (cons 6 "El resultado del test no encontro ningun error en los datos"))
    (setq CONCATENADO (cons 6 "Se encontro un cambio en la media entre los dos intervalos"))
  )
  (setq reportelist2 (append reportelist2 (list CONCATENADO)))
  (setq resultado resultado)
)

;(testcram "001320024500367004100050601004050120705503898" "0013200245003670041000506010040501207055" 3 2)
;lista		cadena		lista de datos en forma de cadena 
;carx		entero		ancho de caracteres en x
;cary		entero		ancho de caracteres en y
