(DEFUN mtoh (AREA)
   (SETQ AREA (aTOf area))
   (setq hec (fix (/ area 10000)))
   (setq dhec (fix (/ (- area (* hec 10000)) 100)))
   (setq chec (- area (* hec 10000) (* dhec 100)))
   (if (= hec 0) (setq thec "0") (setq thec (itoa hec)))
   (if (< dhec 10) (setq tdhec (strcat "0" (itoa dhec))) (setq tdhec (itoa dhec)))
   (if (< chec 10) (setq tchec (strcat "0" (rtos chec 2 3))) (setq tchec (rtos chec 2 3)))
   (setq areaf (strcat thec " - " tdhec " - " tchec))
)
