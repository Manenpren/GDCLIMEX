(defun generaestalistel()
(setq cont 0)
(SETQ estasel2 nil)
(setq estac (cadr(assoc (1+ cont) estaciones3)))
(setq procedencia "CLICOM")
  (while estac
    (setq estasel2 (append estasel2 (LIST(CONS (1+ cont) (cons (strcat (cadr(assoc (1+ cont) estaciones3)) "C") (list   (caddr(assoc (1+ cont) estaciones3)) (cadddr(assoc (1+ cont) estaciones3)) (Ielevacion estac)))))))
    (setq cont(1+ cont))
    (setq estac (cadr(assoc (1+ cont) estaciones3)))
  )
(setq cont 0)
(setq estac (cadr(assoc (1+ cont) estaciones4)))
(setq procedencia "ERIC")
(while estac
    (setq estasel2 (append estasel2 (LIST(CONS (1+ cont) (cons (strcat (cadr(assoc (1+ cont) estaciones4)) "E") (list   (caddr(assoc (1+ cont) estaciones4)) (cadddr(assoc (1+ cont) estaciones4)) (Ielevacion estac)))))))
    (setq cont(1+ cont))
    (setq estac (cadr(assoc (1+ cont) estaciones4)))
  )
)
(defun generamatdisteuc()
(setq cont 1)
(setq matrizeucli "")
(setq estac (cadr(assoc cont estasel2)))
(setq estac2 (cadr(assoc (1+ cont) estasel2)))
(SETQ x (atof(caddr(assoc cont estasel2))))
(SETQ y (atof(cadddr(assoc cont estasel2))))
(SETQ z (atof(last(assoc cont estasel2))))
(SETQ x2 (atof(caddr(assoc (1+ cont) estasel2))))
(SETQ y2 (atof(cadddr(assoc (1+ cont) estasel2))))
(SETQ z2 (atof(last(assoc (1+ cont) estasel2))))
(SETQ dx (-(abs x)(abs x2)))
(SETQ dy (-(abs y)(abs y2)))
(SETQ dz (-(abs z)(abs z2)))
(setq diseuc (itoa(fix(SQRT (+ (* dx dx) (* dy dy) (* dz dz))))))
(setq tamaño (strlen  diseuc))
(while (< tamaño 8)
  (setq diseuc (strcat diseuc " "))
  (setq tamaño (strlen  diseuc))
)	
(setq matrizeucli (strcat matrizeucli estac estac2 diseuc))
(setq estac2 (cadr(assoc (1+ cont) estasel2)))
  (while (and(/= estac2 nil)(/= estac2 ""))
    (setq cont (1+ cont))
    (SETQ x (atof(caddr(assoc cont estasel2))))
    (SETQ y (atof(cadddr(assoc cont estasel2))))
    (SETQ z (atof(last(assoc cont estasel2))))
    (SETQ x2 (atof(caddr(assoc (1+ cont) estasel2))))
    (SETQ y2 (atof(cadddr(assoc (1+ cont) estasel2))))
    (SETQ z2 (atof(last(assoc (1+ cont) estasel2))))
    (SETQ dx (-(abs x)(abs x2)))
    (SETQ dy (-(abs y)(abs y2)))
    (SETQ dz (-(abs z)(abs z2)))
    (setq diseuc (itoa(fix(SQRT (+ (* dx dx) (* dy dy) (* dz dz))))))
    (setq tamaño (strlen  diseuc))
     (while (< tamaño 8)
      (setq diseuc (strcat diseuc " "))
      (setq tamaño (strlen  diseuc))
     )
     (setq matrizeucli (strcat matrizeucli estac estac2 diseuc))
     (setq estac2 (cadr(assoc (1+ cont) estasel2)))
    )
)
