(DEFUN LWPOINT (POLY)
  (SETQ PROV 1)
  (SETQ P1T (VERTICESURF POLI PROV))
  (WHILE P1T
    (setq gpoLP (ssget "C" (suma p1T 0.10 0.10) (suma p1T -0.10 -0.10)))
    (SETQ R (sslength gpoLP))
    (SETQ PROV2 0)
    (setq mdist 100)
    (SETQ OBCOR NIL)
    (REPEAT R
      (SETQ OBJP (ssname gpoLP PROV2))
      (if (= "PUNTO" (cdr (assoc 2 (entget OBJP))))
       (progn
        (SETQ PVT (cdr (assoc 10 (entget OBJP))))
        (setq pdist (distance p1T pvT))
        (if (> mdist pdist)
         (progn
          (setq mdist pdist)
          (setq obcor objP)
         )
        )
       )
      )
      (SETQ PROV2 (1+ PROV2))
    )
    (if (AND (< 0 MDIST) (/= obcor nil))
      (PROGN
       (ALERT "HAY UN BLOCK FUERA DE SU POSICION")
       (SETQ XYZ (cdr (assoc 10 (ENTGET OBCOR))))
       (COMMAND "ZOOM" "C" XYZ "4")
       (COMMAND "CIRCLE" XYZ ".1")
       (SETQ PROVE (ENTLAST))
       (setQ OPT (GETSTRING "DESEAS MOVERLO HACIA LA LINEA (S/N) <S> :"))
       (IF (= "CIRCLE" (cdr (assoc 0 (ENTGET PROVE))))
         (COMMAND "ERASE" PROVE "")
       )
       (IF (= OPT "")
          (SETQ OPT "S") 
       )
       (IF (= OPT "S")
        (PROGN
         (command "MOVE" OBCOR "" (cdr (assoc 10 (entget OBCOR))) P1T)
        )
       )
       (COMMAND "ZOOM" "P")
      )
    )
    (SETQ PROV (1+ PROV))
    (SETQ P1T (VERTICESURF POLI PROV))
  )         

)
