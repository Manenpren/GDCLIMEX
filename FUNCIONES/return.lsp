(defun regresapp()
  (COMMAND "UNDO" "M")
  (LOAD (STRCAT RUTAFAS "ENCUENTRA ESTACIONES CLIMATICAS"))
  (setq contz 0)
  (setq procedencia "")
  (setq ESTACFINALC "")
  (setq ESTACFINALE "")
  (SETQ DIALOGOGRF "0116511052000000000")
  (setq colorgrf "007131141140142152154164166176178")
  (SETQ DATCLIMASOBRE "1")
  (SETQ BDPOLI (VERTICEBD LINEA))
  (setq CENTROIDEC (ax:centroid LINEA))
  (if (= zonah nil) (setq zonah "00"))
  (setq lzona (gzona))
  (setq zonah (itoa (caddr lzona)))
  (setq xyz (list (car CENTROIDEC) (cadr CENTROIDEC)))
  (setq puntogeo (UTM-GEO xyz (ATOI ZONAH)))
  (SETQ CUEVER 0)
  (setq verpol (cdr (assoc cuever BDPOLI)))
  (SETQ XMIN (RTOS (car VERPOL) 2 5))
  (SETQ YMIN (RTOS (caDr VERPOL) 2 5))
  (SETQ XMAX (RTOS (car VERPOL) 2 5))
  (SETQ YMAX (RTOS (caDr VERPOL) 2 5))
  (SETQ matrizd NIL)
  (WHILE VERPOL
    (setq puntogeox (UTM-GEO (list (car verpol) (cadr verpol)) (ATOI ZONAH)))
    (setq CONCATENADOx (cons cuever puntogeox))
    (setq matrizd (append matrizd (list CONCATENADOx)))
    (SETQ XI (RTOS (car VERPOL) 2 5))
    (SETQ YI (RTOS (caDr VERPOL) 2 5))
    (IF (> XI XMAX)(SETQ XMAX XI))
    (IF (< XI XMIN)(SETQ XMIN XI))
    (IF (> YI YMAX)(SETQ YMAX YI))
    (IF (< YI YMIN)(SETQ YMIN YI))
    (SETQ CUEVER (1+ CUEVER))
    (setq verpol (cdr (assoc cuever BDPOLI)))
  )
  (if (> (abs (- (atof xmin) (atof xmax))) (abs (- (atof ymin) (atof ymax))))
    (setq dbus (fix (* 0.6 (abs (- (atof xmin) (atof xmax))))))
    (setq dbus (fix (* 0.6 (abs (- (atof ymin) (atof ymax))))))
  )
  (setq GBMIN (list (- (car CENTROIDEC) DBUS) (- (cadr CENTROIDEC) DBUS)))
  (setq GBMAX (list (+ (car CENTROIDEC) DBUS) (+ (cadr CENTROIDEC) DBUS)))
  (setq GBMIN (UTM-GEO GBMIN (ATOI ZONAH)))
  (setq GBMAX (UTM-GEO GBMAX (ATOI ZONAH)))
  (busca gbmin gbmax)
  (while (and (= estaciones nil) (= estaciones2 nil))
    (dos_splash (strcat ruta "ajuste.htj") 2)
    (setq dbus (* 1.4 dbus))
    (setq GBMIN (list (- (car CENTROIDEC) DBUS) (- (cadr CENTROIDEC) DBUS)))
    (setq GBMAX (list (+ (car CENTROIDEC) DBUS) (+ (cadr CENTROIDEC) DBUS)))
    (setq GBMIN (UTM-GEO GBMIN (ATOI ZONAH)))
    (setq GBMAX (UTM-GEO GBMAX (ATOI ZONAH)))
    (busca gbmin gbmax)
  );while
  (setq nest 1)
  (dialogox)
  (if (= opbusqueda "s") (segundop))
  (while (= opbusqueda "b")
    (setq GBMIN (list (- (car CENTROIDEC) DBUS) (- (cadr CENTROIDEC) DBUS)))
    (setq GBMAX (list (+ (car CENTROIDEC) DBUS) (+ (cadr CENTROIDEC) DBUS)))
    (setq GBMIN (UTM-GEO GBMIN (ATOI ZONAH)))
    (setq GBMAX (UTM-GEO GBMAX (ATOI ZONAH)))
    (busca gbmin gbmax)
    (while (and (= estaciones nil) (= estaciones2 nil))
      (dos_splash (strcat ruta "ajuste.htj") 2)
      (setq dbus (* 1.4 dbus))
      (setq GBMIN (list (- (car CENTROIDEC) DBUS) (- (cadr CENTROIDEC) DBUS)))
      (setq GBMAX (list (+ (car CENTROIDEC) DBUS) (+ (cadr CENTROIDEC) DBUS)))
      (setq GBMIN (UTM-GEO GBMIN (ATOI ZONAH)))
      (setq GBMAX (UTM-GEO GBMAX (ATOI ZONAH)))
      (busca gbmin gbmax)
    );while
    (dialogox)
  )
  (load (strcat RUTAFAS "revisa datos climatologicos"))
  (segundop)
)
