(defun regresionl (estacion procedencia variable fechaini fechafin tipodat tipoproceso)
  (C:LIBRERIA "lee datos estacion")
  (C:LIBRERIA "media ar")
  (C:LIBRERIA "suma cuadrados")
  (C:LIBRERIA "suma cuadradosx")
  (C:LIBRERIA "media arx")
  (C:LIBRERIA "media ar")
  (C:LIBRERIA "suma")
  (C:LIBRERIA "sumax")
  (C:LIBRERIA "multiplicaxy")
;  (setq fechaini "190001")
          (if (AND (OR (= variable 1) (= variable 3)) (OR (= tipoproceso "MA") (= tipoproceso "MI") (= tipoproceso "ME")))
            (SETQ CARY 6)
           )
          (if (AND (OR (= variable 7) (= variable 8) (= variable 9)) (OR (= tipoproceso "MA") (= tipoproceso "MI") (= tipoproceso "ME")) )
            (SETQ CARY 5)
          )
          (if (= tipoproceso "TO")
           (SETQ CARY 9)
          )
          (if (= tipoproceso "VC")
           (SETQ CARY 5)
          )
          (if (and (or (= variable 2) (= variable 4) (= variable 5) (= variable 6)) (/= tipoproceso "VC"))
            (SETQ CARY 1)
          )
          (if (= tipodat "ST") (setq carx 6))
          (if (/= tipodat "ST") (setq carx 4))
  (setq caracterprov "")
  (repeat CARY
    (setq caracterprov (strcat caracterprov "x"))
  )
  (setq datoex (leebd estacion procedencia variable fechaini tipodat tipoproceso))
  (setq listacon (smeses datoex))
  (setq contx 1)
  (setq ecuaciones nil)
  (repeat 12
    (SETQ ecuacion (regrelineal (CDR (ASSOC contx LISTACON))))
    (setq CONCATENADO (cons contx ecuacion)) 
    (setq ecuaciones (append ecuaciones (list CONCATENADO)))
    (setq contx (1+ contx))
  )
  (setq ecuaciones ecuaciones)
) ;(mediaarx (CDR (ASSOC contx LISTACON)) 4 cary)

(defun regrelineal (datoexs)
  (setq mediaxx (mediaarx datoexs 4 cary))
  (setq mediay (mediaar datoexs 4 cary))
  (setq scuadrax (sumacuadx datoexs 4 cary))
  (setq scuadray (sumacuad datoexs 4 cary))
  (setq sumanx (sumaxx datoexs 4 cary))
  (setq sumany (sumax datoexs 4 cary))
  (setq mlxy (multiplicaxy datoexs 4 cary))
  (setq b1 (/ (- mlxy (* mediay sumanx)) (- scuadrax (* mediaxx sumanx))))
  (setq b0 (- mediay (* b1 mediaxx)))
  (setq rr (/ (+ (* b0 sumany) (* b1 mlxy) (* -1 nelementx (expt mediay 2))) (- scuadray (* (1- nelementx) (expt mediay 2)))))
  (setq resultado (list b1 b0 rr)) 
)

(defun smeses (datoexs)
  (setq nmeses (/ (strlen datoexs) (+ carx cary)))
  (setq datene "")
  (setq datfeb "")
  (setq datmar "")
  (setq databr "")
  (setq datmay "")
  (setq datjun "")
  (setq datjul "")
  (setq datago "")
  (setq datsep "")
  (setq datoct "")
  (setq datnov "")
  (setq datdic "")
  (setq contt 1)
  (repeat nmeses
    (setq datomen (substr datoexs (1+ (* (1- contt) (+ carx cary))) (+ carx cary)))
    (setq coordmes (/ (atoi (substr datomen 1 carx)) 12.00))
    (setq coordmesfan (fix (/ (atoi (substr datomen 1 carx)) 12)))
    (setq difer (rtos (- coordmes coordmesfan) 2 3))
    (if (= difer "0.083") (setq datene (strcat datene (itoa (+ 1900 coordmesfan)) (substr datomen (1+ carx) cary))))
    (if (= difer "0.167") (setq datfeb (strcat datFEB (itoa (+ 1900 coordmesfan)) (substr datomen (1+ carx) cary))))
    (if (or (= difer "0.250") (= difer "0.25")) (setq datmar (strcat datMAR (itoa (+ 1900 coordmesfan)) (substr datomen (1+ carx) cary))))
    (if (= difer "0.333") (setq databr (strcat datABR (itoa (+ 1900 coordmesfan)) (substr datomen (1+ carx) cary))))
    (if (= difer "0.417") (setq datmay (strcat datMAY (itoa (+ 1900 coordmesfan)) (substr datomen (1+ carx) cary))))
    (if (or (= difer "0.500") (= difer "0.5")) (setq datjun (strcat datJUN (itoa (+ 1900 coordmesfan)) (substr datomen (1+ carx) cary))))
    (if (= difer "0.583") (setq datjul (strcat datJUL (itoa (+ 1900 coordmesfan)) (substr datomen (1+ carx) cary))))
    (if (= difer "0.667") (setq datago (strcat datAGO (itoa (+ 1900 coordmesfan)) (substr datomen (1+ carx) cary))))
    (if (or (= difer "0.750") (= difer "0.75")) (setq datsep (strcat datSEP (itoa (+ 1900 coordmesfan)) (substr datomen (1+ carx) cary))))
    (if (= difer "0.833") (setq datoct (strcat datOCT (itoa (+ 1900 coordmesfan)) (substr datomen (1+ carx) cary))))
    (if (= difer "0.917") (setq datnov (strcat datNOV (itoa (+ 1900 coordmesfan)) (substr datomen (1+ carx) cary))))
    (if (or (= difer "0.000") (= difer "0")) (setq datdic (strcat datDIC (itoa (+ 1900 coordmesfan)) (substr datomen (1+ carx) cary))))
    (setq contt (1+ contt))
  )
  (setq resultado nil)
   (setq CONCATENADO (cons 1 datene)) 
   (setq resultado (append resultado (list CONCATENADO)))
   (setq CONCATENADO (cons 2 datfeb)) 
   (setq resultado (append resultado (list CONCATENADO)))
   (setq CONCATENADO (cons 3 datmar)) 
   (setq resultado (append resultado (list CONCATENADO)))
   (setq CONCATENADO (cons 4 databr)) 
   (setq resultado (append resultado (list CONCATENADO)))
   (setq CONCATENADO (cons 5 datmay)) 
   (setq resultado (append resultado (list CONCATENADO)))
   (setq CONCATENADO (cons 6 datjun)) 
   (setq resultado (append resultado (list CONCATENADO)))
   (setq CONCATENADO (cons 7 datjul)) 
   (setq resultado (append resultado (list CONCATENADO)))
   (setq CONCATENADO (cons 8 datago)) 
   (setq resultado (append resultado (list CONCATENADO)))
   (setq CONCATENADO (cons 9 datsep)) 
   (setq resultado (append resultado (list CONCATENADO)))
   (setq CONCATENADO (cons 10 datoct)) 
   (setq resultado (append resultado (list CONCATENADO)))
   (setq CONCATENADO (cons 11 datnov)) 
   (setq resultado (append resultado (list CONCATENADO)))
   (setq CONCATENADO (cons 12 datdic)) 
   (setq resultado (append resultado (list CONCATENADO)))
)

;(regresionl "16087" "C" 3 "ME" "ME")
;estacion	cadena		estacion a graficar
;procedencia	cadena		Clicom o erick
;variable	entero		variable climatica a graficar 1-9
;FECHAINI	CADENA		FECHA INICIAL A PROCESAR LOS DATOS DE LA GRAFICA formato de 4 6 o 8 caracteres segun se requiera
;tipodat	CADENA		tipo de datos a graficar "AN" "ME" "ST" "MM"
;tipoproceso	cadena		tipo de proceso a recibir la cadena (valores maximos, minimos, medios, totales, %vacios, serie temporal) "MA" "MI" "ME" "TO" "VC" "ST"
