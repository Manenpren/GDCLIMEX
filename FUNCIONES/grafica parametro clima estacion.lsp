(DEFUN graficaestac (estacion procedencia variable fuente lgui cotas color tipo FECHAINI fechafin hini hfin tipodat tipoproceso)
  (C:LIBRERIA "lineas guia")
  (C:LIBRERIA "GRAFICAX")
  (C:LIBRERIA "serie temporal diaria")
  (C:LIBRERIA "tranforma coordenadas dibujo im dconcatenados")
  (C:LIBRERIA "CONVIERTE NUMERO EN CADENA")
  (C:LIBRERIA "minimos")
  (C:LIBRERIA "maximos")
  (C:LIBRERIA "media")
  (C:LIBRERIA "porcentajes")
  (C:LIBRERIA "totales")
  (setq numeroelem (cuentae))
  (if (= fuente "V")
    (progn
      (if (= tipodat "AN")
        (progn
          (if (> (atoi estacion) nestclicom)
            (setq ldat (cdr (assoc (- (atoi estacion) nestclicom) matrizporcentaje)))
            (setq ldat (cdr (assoc (atoi estacion) matrizporcentajc)))
          )
          (setq ldat (cdr (assoc (atoi variable) ldat)))
          (setq ldat1 (substr ldat 22))
          (SETQ CARX 4)
          (SETQ CARY 5)
        )
      )
    )
  )
  (if (= fuente "A")
    (progn
      (if (= procedencia "C")
        (progn
          (setq diradicional "CLICOM")
          (setq extencion ".cli")
        )
        (progn
          (setq diradicional "ERIC")
          (setq extencion ".clk")
        )
      )
      (if (= variable 1) (progn (setq dirprim "\\evapora\\") (setq ndec 2) (setq anchochr 6)))
      (if (= variable 2) (progn (setq dirprim "\\granizo\\") (setq ndec 0) (setq anchochr 1)))
      (if (= variable 3) (progn (setq dirprim "\\hp\\") (setq ndec 2) (setq anchochr 6)))
      (if (= variable 4) (progn (setq dirprim "\\neblina\\") (setq ndec 0) (setq anchochr 1)))
      (if (= variable 5) (progn (setq dirprim "\\nublado\\") (setq ndec 0) (setq anchochr 1)))
      (if (= variable 6) (progn (setq dirprim "\\rayos\\") (setq ndec 0) (setq anchochr 1)))
      (if (= variable 7) (progn (setq dirprim "\\temp\\") (setq ndec 2) (setq anchochr 5)))
      (if (= variable 8) (progn (setq dirprim "\\tempmax\\") (setq ndec 2) (setq anchochr 5)))
      (if (= variable 9) (progn (setq dirprim "\\tempmin\\") (setq ndec 2) (setq anchochr 5)))
      (setq ldat1 "")
      (if (and (= procedencia "E") (/= optimizadiarioe nil)) (setq ldat1 (optimizabdiarios)))
      (if (and (= procedencia "C") (/= optimizadiarioc nil)) (setq ldat1 (optimizabdiarios)))
      (if (= ldat1 "")
        (progn      
          (dos_getcancel "LEYENDO BD" "LEYENDO DATOS POR FAVOR ESPERE...")
          (IF (not (dos_getcanceL)) (exit))
          (dos_encrypt (strcat ruta "BASES DE DATOS\\DATOS CLIMATOLOGICOS\\" diradicional dirprim estacion extencion) (strcat "4avEjsD8GlñOpwrpfvc3071fdA" estacion "Ga4TykP8G5Umo9Ye513"))
          (setq archIVOindice (open (strcat ruta "BASES DE DATOS\\DATOS CLIMATOLOGICOS\\" diradicional dirprim estacion extencion) "r"))
          (setq ldat1x (read-line archIVOindice))
          (close archivoindice)
          (dos_encrypt (strcat ruta "BASES DE DATOS\\DATOS CLIMATOLOGICOS\\" diradicional dirprim estacion extencion) (strcat "4avEjsD8GlñOpwrpfvc3071fdA" estacion "Ga4TykP8G5Umo9Ye513"))
          (IF (not (dos_getcanceL)) (exit))
          (setq ldat1 (descompacta ldat1x))
          (IF (not (dos_getcanceL)) (exit))          
          (if (= procedencia "E")
            (progn
              (if (= controlbdace nil) (setq controlbdace 1))
              (setq cadenaprov (strcat estacion (itoa variable)))
              (setq valorx (list (cons 1 cadenaprov) (cons 2 ldat1)))
              (setq CONCATENADO (cons controlbdace valorx)) 
              (setq optimizadiarioe (append optimizadiarioe (list CONCATENADO)))
              (setq controlbdace (1+ controlbdace))
            )
          )
          (if (= procedencia "C")
            (progn
              (if (= controlbdacc nil) (setq controlbdacc 1))
              (setq cadenaprov (strcat estacion (itoa variable)))
              (setq valorx (list (cons 1 cadenaprov) (cons 2 ldat1)))
              (setq CONCATENADO (cons controlbdacC valorx)) 
              (setq optimizadiarioC (append optimizadiarioC (list CONCATENADO)))
              (setq controlbdacc (1+ controlbdacc))
            )
          )
          (dos_getcanceL t)
        )
      );if 
      (if (OR (= tipodat "AN") (= tipodat "ME") (= tipodat "MM"))
        (progn
          (if (= tipoproceso "MA") (setq ldat1 (maximos ldat1 tipodat variable fechaini)))
          (if (= tipoproceso "MI") (setq ldat1 (minimos ldat1 tipodat variable fechaini)))
          (if (= tipoproceso "ME") (setq ldat1 (media ldat1 tipodat variable fechaini)))
          (if (= tipoproceso "TO") (setq ldat1 (TOTALES ldat1 tipodat variable fechaini)))
          (if (= tipoproceso "VC") (setq ldat1 (PORCENTAJES ldat1 tipodat variable fechaini)))
          (if (AND (OR (= variable 1) (= variable 3)) (OR (= tipoproceso "MA") (= tipoproceso "MI") (= tipoproceso "ME")))
            (SETQ CARY 6)
          )
          (if (AND (OR (= variable 7) (= variable 8) (= variable 9)) (OR (= tipoproceso "MA") (= tipoproceso "MI") (= tipoproceso "ME")) )
            (SETQ CARY 5)
          )
          (if (= tipoproceso "TO")
            (progn
              (if (= variable 1) (progn (setq ndec 2) (setq CARY 9)))
              (if (= variable 2) (progn (setq ndec 0) (setq CARY 4)))
              (if (= variable 3) (progn (setq ndec 2) (setq CARY 9)))
              (if (= variable 4) (progn (setq ndec 0) (setq CARY 4)))
              (if (= variable 5) (progn (setq ndec 0) (setq CARY 4)))
              (if (= variable 6) (progn (setq ndec 0) (setq CARY 4)))
              (if (= variable 7) (progn (setq ndec 2) (setq CARY 8)))
              (if (= variable 8) (progn (setq ndec 2) (setq CARY 8)))
              (if (= variable 9) (progn (setq ndec 2) (setq CARY 8)))
            )
          )
          (if (= tipoproceso "VC")
            (SETQ CARY 5)
          )
          (if (and (or (= variable 2) (= variable 4) (= variable 5) (= variable 6)) (/= tipoproceso "VC"))
            (SETQ CARY 1)
          )
        )
      )
      (if (= tipodat "ST") (setq ldat1 (tempdiaria ldat1 variable fechaini)))
      (if (= tipodat "ST")
        (PROGN
          (SETQ CARX 6)
          (SETQ CARY ANCHOCHR)
        )
        (SETQ CARX 4)
      )
    )
  )
  (setq hfinx (escaneah))
  (if (> hfinx hfin) (setq hfin hfinx))
  (setq anchorealx (1+(- (atoi (substr fechafin 1 4)) (atoi (substr fechaini 1 4)))))
  (setq anchorealy (- hfin hini))
  (if (> anchorealx 1)
    (progn
      (setq sretpx (fix (/ (* 10 anchorealx) 100)))
      (setq sretsx (/ sretpx 6.0))
    )
    (progn
      (setq sretpx 1)
      (setq sretsx 0.083333)
    )
  )
  (setq sretpy (/ anchorealy 5.0))
  (setq sretsy (/ sretpy 2.0))
  (if (= lgui "S")
    (lineasgui 269 354 500 240 anchorealx anchorealy sretpx sretsx sretpy sretsy "SI" "SI" "SI" "SI" 251 251 251 251)
  )
  (graficax 500.000 240.000 NUMEROELEM anchorealy 269.000 114.000 1 hini ldat1 CARX CARY "NO" "NO" 1 (/ (strlen ldat1) (+ carx cary)) TIPO color "SI");111 114
  (if (= cotas "S")
    (progn
      (acotagrf 269 354 500.000 anchorealx (atoi (substr fechaini 1 4)) sretpx sretsx 1 2 15 6 "SI" "NO" 7 7 4 1 8 8 "X" "romans" "romans" 3 3)
      (acotagrf 269 354 240.000 anchorealy hini sretpy sretsy 1 2 15 6 "SI" "NO" 7 7 3 1 8 8 "Y" "romans" "romans" 3 3)
    )
  )
  (if (and (= lgui "S") (= cotas "S"))
   (progn
    (if (AND (= variable 1) (/= tipoproceso "VC"))
      (progn
        (slide_image 192 128 60 220 (STRCAT RUTA "SLIDES\\detallesgrf(EVAP)"))
      )
    )
    (if (AND (= variable 3) (/= tipoproceso "VC"))
      (progn
        (slide_image 192 128 50 220 (STRCAT RUTA "SLIDES\\detallesgrf(HP)"))
      )
    )
    (if (AND (OR (= variable 7) (= variable 8) (= variable 9)) (/= tipoproceso "VC"))
      (progn
        (slide_image 192 128 48 200 (STRCAT RUTA "SLIDES\\detallesgrf(TEMP)"))
      )
    )
    (if (AND (OR (= variable 2) (= variable 4) (= variable 5) (= variable 6)) (/= tipoproceso "VC"))
      (progn
        (slide_image 200 120 25 135 (STRCAT RUTA "SLIDES\\detallesgrf(DIAS)"))
      )
    )
    (if (/= tipodat "MM")
      (slide_image 496 398 53 18 (STRCAT RUTA "SLIDES\\años"))
    )
    (if (= tipoproceso "VC")
      (slide_image 192 128 40 180 (STRCAT RUTA "SLIDES\\detallesgrf(VACIOS)"))
    )
    (setq titulo1 "")
    (setq titulo2 "")
    (setq titulo3 "")
    (setq titulof (titulo))
    (stexto TITULOF "romans" 22 274 73)
    (stexto ESTACION "romans" 28 744 445)
    (stexto (nombreestado) "romans" 22 184 450) 
    (stexto (denominacion) "romans" 22 383 450)
   )
  )
  (stexto (nombrevarclim) "romans" 13 777 (+ 134 (* 22 (1- variable))))
  (muestracl color 777 (+ 146 (* 22 (1- variable))) 52 8)
) 

(defun nombrevarclim ()
  (if (= variable 1) (setq resultado "Evap."))
  (if (= variable 2) (setq resultado "Gran."))
  (if (= variable 3) (setq resultado "Precip."))
  (if (= variable 4) (setq resultado "Neblina."))
  (if (= variable 5) (setq resultado "Cobert."))
  (if (= variable 6) (setq resultado "Torm."))
  (if (= variable 7) (setq resultado "Temp."))
  (if (= variable 8) (setq resultado "Temp mx"))
  (if (= variable 9) (setq resultado "Temp mi"))
  (setq resultado resultado)
)

(defun escaneah ()
  (setq nciclos (/ (strlen ldat1) (+ carx cary)))
  (setq contcicloes 0)
  (setq maxvalory nil)
  (repeat nciclos
    (setq elementoex (substr ldat1 (+ 1 carx (* contcicloes (+ carx cary))) cary))
    (if (= maxvalory nil) (setq maxvalory elementoex))
    (if (< (atof maxvalory) (atof elementoex)) (setq maxvalory elementoex))
    (setq contcicloes (1+ contcicloes))
  )
  (if (/= maxvalory nil)
    (setq maxvalory (1+ (fix (atof maxvalory))))
    (setq maxvalory 100)
  )
)

(defun denominacion ()
  (if (= procedencia "C")
    (progn
      (setq contcig 1)
      (setq estaciong (substr bdmemclicom 1 58))
      (while (and (/= estacion (vl-string-trim " " (substr estaciong 1 5))) (< (1- contcig) (/ (strlen indiceclicom) 6)))
        (setq estaciong (substr bdmemclicom (+ 1 (* (1- (atoi (substr indiceclicom (1+ (* (1- contcig) 6)) 6))) 58)) 58))
        (setq contcig (1+ contcig))
      )
      (setq denominacionv (vl-string-trim " " (substr estaciong 6 24)))
    )
    (progn
      (setq contcig 1)
      (setq estaciong (substr bdmemeric 1 58))
      (while (and (/= estacion (vl-string-trim " " (substr estaciong 1 5))) (< (1- contcig) (/ (strlen indiceeric) 6)))
        (setq estaciong (substr bdmemeric (+ 1 (* (1- (atoi (substr indiceeric (1+ (* (1- contcig) 6)) 6))) 58)) 58))
        (setq contcig (1+ contcig))
      )
      (setq denominacionv (vl-string-trim " " (substr estaciong 6 24)))
    )
  )
  (setq denominacionv denominacionv)
)

(defun optimizabdiarios ()
  (if (= procedencia "C")
    (progn
      (setq contcig 1)
      (setq estaciong "000000")
      (setq scierto "")
      (while (and (or (/= estacion (substr estaciong 1 5)) (/= VARIABLE (ATOI (substr estaciong 6 1)))) (< contcig controlbdacc))
        (setq estaciong (cdr (car (cdr (assoc contcig optimizadiarioc)))))
        (if (and (= estacion (substr estaciong 1 5)) (= VARIABLE (ATOI (substr estaciong 6 1)))) (setq scierto "s"))
        (setq contcig (1+ contcig))
      )
      (IF (= scierto "s")
        (setq listadat (cdr (cadr (cdr (assoc (1- contcig) optimizadiarioc)))))
        (setq listadat "")
      )
    )
    (progn
      (setq contcig 1)
      (setq estaciong "000000")
      (setq scierto "")
      (while (and (or (/= estacion (substr estaciong 1 5)) (/= VARIABLE (ATOI (substr estaciong 6 1)))) (< contcig controlbdacE))
        (setq estaciong (cdr (car (cdr (assoc contcig optimizadiarioe)))))
        (if (and (= estacion (substr estaciong 1 5)) (= VARIABLE (ATOI (substr estaciong 6 1)))) (setq scierto "s"))
        (setq contcig (1+ contcig))
      )
      (IF (= scierto "s")
        (setq listadat (cdr (cadr (cdr (assoc (1- contcig) optimizadiarioe)))))
        (setq listadat "")
      )
    )
  )
  (setq listadat listadat)
)

(defun nombreestado ()
  (setq estado (substr "01Aguascalientes      02Baja California     03Baja California Sur 04Campeche            05Coahuila de Zaragoza06Colima              07Chiapas             08Chihuahua           09Distrito Federal    10Durango             11Guanajuato          12Guerrero            13Hidalgo             14Jalisco             15México              16Michoacán de Ocampo 17Morelos             18Nayarit             19Nuevo León          20Oaxaca              21Puebla              22Querétaro           23Quintana Roo        24San Luis Potosí     25Sinaloa             26Sonora              27Tabasco             28Tamaulipas          29Tlaxcala            30Veracruz            31Yucatán             32Zacatecas           " (+ 3 (* (1- (atoi (substr estacion 1 (- (strlen estacion) 3)))) 22)) 20))
  (SETQ estado (vl-string-trim " " estado))
)

(defun titulo ()
  (if (= variable 1)
    (setq titulo1 "EVAPORACION")
  )
  (if (= variable 2)
    (setq titulo1 "GRANIZO")
  )
  (if (= variable 3)
    (setq titulo1 "PRECIPITACION")
  )
  (if (= variable 4)
    (setq titulo1 "NEBLINA")
  )
  (if (= variable 5)
    (setq titulo1 "COVERTURA DEL CIELO")
  )
  (if (= variable 6)
    (setq titulo1 "TORMENTAS ELECTRICAS")
  )
  (if (= variable 7)
    (setq titulo1 "TEMPERATURA")
  )
  (if (= variable 8)
    (setq titulo1 "TEMPERATURA MAXIMA")
  )
  (if (= variable 9)
    (setq titulo1 "TEMPERATURA MINIMA")
  )
  (if (= tipodat "AN")
    (SETQ TITULO2 "ANUAL")
  )
  (if (= tipodat "ME")
    (SETQ TITULO2 "MENSUAL")
  )
  (if (= tipodat "MM")
    (SETQ TITULO2 "MEDIA MENSUAL")
  )
  (if (= tipodat "ST")
    (SETQ TITULO2 "DIARIA")
  )
  (if (= tipoproceso "MA") (setq TITULO3 "MAXIMA"))
  (if (= tipoproceso "MI") (setq TITULO3 "MINIMA"))
  (if (= tipoproceso "ME") (setq TITULO3 "MEDIA"))
  (if (= tipoproceso "TO") (setq TITULO3 "TOTAL"))
  (if (= tipoproceso "VC") (setq TITULO3 ""))
  (SETQ TITULOX (STRCAT TITULO1 " " TITULO3 " " TITULO2))
)

(defun cuentae ()
  (if (= tipodat "AN")
    (setq nelementos (- (atoi (substr fechafin 1 4)) (atoi (substr fechaini 1 4))))
  )
  (if (= tipodat "ME")
    (progn
      (setq fret fechaini)
      (setq nelementos 1)
      (while (/= fret fechafin)
        (setq fret (mesmas fret))
        (setq nelementos (1+ nelementos))
      )
    )
  )
  (if (= tipodat "ST")
    (progn
      (setq fret (substr fechaini 1 6))
      (setq nelementos 1)
      (while (/= fret (substr fechafin 1 6))
        (setq mes (substr fret 5 2))
        (if (= mes "01") (setq ndias 31))
        (if (= mes "03") (setq ndias 31))
        (if (= mes "04") (setq ndias 30))
        (if (= mes "05") (setq ndias 31))
        (if (= mes "06") (setq ndias 30))
        (if (= mes "07") (setq ndias 31))
        (if (= mes "08") (setq ndias 31))
        (if (= mes "09") (setq ndias 30))
        (if (= mes "10") (setq ndias 31))
        (if (= mes "11") (setq ndias 30))
        (if (= mes "12") (setq ndias 31))
        (if (= mes "02")
          (progn
            (setq fx (atoi (substr fret 1 4)))
            (setq dx (* (fix (/ fx 4)) 4))
            (if (= dx fx)
               (setq ndias 29)
               (setq ndias 28)
            )
          )
        );if
        (setq fret (mesmas fret))
        (if (= nelementos 0)
          (setq nelementos (+ nelementos (- ndias (1- (atoi (substr fechaini 7 2))))))
          (setq nelementos (+ nelementos ndias))
        )
      )
      (setq mes (substr fret 5 2))
      (if (= mes "01") (setq ndias 31))
      (if (= mes "03") (setq ndias 31))
      (if (= mes "04") (setq ndias 30))
      (if (= mes "05") (setq ndias 31))
      (if (= mes "06") (setq ndias 30))
      (if (= mes "07") (setq ndias 31))
      (if (= mes "08") (setq ndias 31))
      (if (= mes "09") (setq ndias 30))
      (if (= mes "10") (setq ndias 31))
      (if (= mes "11") (setq ndias 30))
      (if (= mes "12") (setq ndias 31))
      (if (= mes "02")
        (progn
          (setq fx (atoi (substr fret 1 4)))
          (setq dx (* (fix (/ fx 4)) 4))
          (if (= dx fx)
             (setq ndias 29)
             (setq ndias 28)
          )
        )
      );if
      (setq nelementos (+ nelementos ndias))
      (setq nelementos (- nelementos (- ndias (1- (atoi (substr fechafin 7 2))))))
    );progn
  )
  (if (= tipodat "MM")
    (setq nelementos 12)
  )
  (setq nelementos nelementos)
)

(defun mesmas (fecha)
  (setq mes (substr fecha 5 2))
  (if (= mes "12")
    (progn
      (setq amo (1+ (atoi (substr fecha 1 4))))
      (setq fechaf (strcat (itoa amo) "01"))
    )
    (progn
      (setq fechaf (strcat (substr fecha 1 4) (NTOCAD (1+ (atoi (substr fecha 5 2))) 0 2)))
    )
  )
  (setq fechaf fechaf)
)

;(setq x (append (list (cons 1 (list (cons 1 "1-1") (cons 2 "1-2"))) (cons 2 (list (cons 1 "2-1") (cons 2 "2-2"))) (cons 3 (list (cons 1 "3-1") (cons 2 "3-2"))))))
;estacion	cadena		estacion a graficar
;procedencia	cadena		Clicom o erick
;variable	entero		variable climatica a graficar 1-9
;fuente		cadena		fuente de los datos "archivo o variable" "A" "V"
;lgui		cadena		dibujar o no las lineas guia "S" "N"
;cotas		cadena		dibujar o no las cotas "S" "N"
;color		cadena		color de la grafica (4 valores de cadena con el formato de variable de dialogo grafica) "007131141140142152154164166176178"
;tipo		cadena		de barras de lineas de puntos "DS" "BR" "LI"
;FECHAINI	CADENA		FECHA INICIAL A PROCESAR LOS DATOS DE LA GRAFICA formato de 4 6 o 8 caracteres segun se requiera
;FECHAfin	CADENA		FECHA final A PROCESAR LOS DATOS DE LA GRAFICA formato de 4 6 o 8 caracteres segun se requiera
;hini		REAL		altura de la grafica inicial
;hfin		REAL		altura de la grafica final
;tipodat	CADENA		tipo de datos a graficar "AN" "ME" "ST" "MM"
;tipoproceso	cadena		tipo de proceso a recibir la cadena (valores maximos, minimos, medios, totales, %vacios, serie temporal) "MA" "MI" "ME" "TO" "VC" "ST"}

(defun graficaestac2 (estacion procedencia variable fuente lgui cotas color tipo FECHAINI fechafin hini hfin tipodat tipoproceso)
  (C:LIBRERIA "lineas guia")
  (C:LIBRERIA "GRAFICAX")
  (C:LIBRERIA "serie temporal diaria")
  (C:LIBRERIA "tranforma coordenadas dibujo im dconcatenados")
  (C:LIBRERIA "CONVIERTE NUMERO EN CADENA")
  (C:LIBRERIA "minimos")
  (C:LIBRERIA "maximos")
  (C:LIBRERIA "media")
  (C:LIBRERIA "porcentajes")
  (C:LIBRERIA "totales")
  (setq procedencia (substr procedencia 1 1))
  (setq numeroelem (cuentae))
  (if (= fuente "V")
    (progn
      (if (= tipodat "AN")
        (progn
          (if (> (atoi estacion) nestclicom)
            (setq ldat (cdr (assoc (- (atoi estacion) nestclicom) matrizporcentaje)))
            (setq ldat (cdr (assoc (atoi estacion) matrizporcentajc)))
          )
          (setq ldat (cdr (assoc (atoi variable) ldat)))
          (setq ldat1 (substr ldat 22))
          (SETQ CARX 4)
          (SETQ CARY 5)
        )
      )
    )
  )
  (if (= fuente "A")
    (progn
      (if (= procedencia "C")
        (progn
          (setq diradicional "CLICOM")
          (setq extencion ".cli")
        )
        (progn
          (setq diradicional "ERIC")
          (setq extencion ".clk")
        )
      )
      (if (= variable 1) (progn (setq dirprim "\\evapora\\") (setq ndec 2) (setq anchochr 6)))
      (if (= variable 2) (progn (setq dirprim "\\granizo\\") (setq ndec 0) (setq anchochr 1)))
      (if (= variable 3) (progn (setq dirprim "\\hp\\") (setq ndec 2) (setq anchochr 6)))
      (if (= variable 4) (progn (setq dirprim "\\neblina\\") (setq ndec 0) (setq anchochr 1)))
      (if (= variable 5) (progn (setq dirprim "\\nublado\\") (setq ndec 0) (setq anchochr 1)))
      (if (= variable 6) (progn (setq dirprim "\\rayos\\") (setq ndec 0) (setq anchochr 1)))
      (if (= variable 7) (progn (setq dirprim "\\temp\\") (setq ndec 2) (setq anchochr 5)))
      (if (= variable 8) (progn (setq dirprim "\\tempmax\\") (setq ndec 2) (setq anchochr 5)))
      (if (= variable 9) (progn (setq dirprim "\\tempmin\\") (setq ndec 2) (setq anchochr 5)))
      (setq ldat1 "")
;      (if (and (= procedencia "E") (/= optimizadiarioe nil)) (setq ldat1 (leebd estacion procedencia variable fechaini tipodat tipoproceso)))
;      (if (and (= procedencia "C") (/= optimizadiarioc nil)) (setq ldat1 (leebd estacion procedencia variable fechaini tipodat tipoproceso)))
      (if (and (= procedencia "E") (/= optimizadiarioe nil)) (setq ldat1 (optimizabdiarios)))
      (if (and (= procedencia "C") (/= optimizadiarioc nil)) (setq ldat1 (optimizabdiarios)))
      (if (= ldat1 "")
        (progn      
          (dos_getcancel "LEYENDO BD" "LEYENDO DATOS POR FAVOR ESPERE...")
          (IF (not (dos_getcanceL)) (exit))
          (dos_encrypt (strcat ruta "BASES DE DATOS\\DATOS CLIMATOLOGICOS\\" diradicional dirprim estacion extencion) (strcat "4avEjsD8GlñOpwrpfvc3071fdA" estacion "Ga4TykP8G5Umo9Ye513"))
          (setq archIVOindice (open (strcat ruta "BASES DE DATOS\\DATOS CLIMATOLOGICOS\\" diradicional dirprim estacion extencion) "r"))
          (setq ldat1x (read-line archIVOindice))
          (close archivoindice)
          (dos_encrypt (strcat ruta "BASES DE DATOS\\DATOS CLIMATOLOGICOS\\" diradicional dirprim estacion extencion) (strcat "4avEjsD8GlñOpwrpfvc3071fdA" estacion "Ga4TykP8G5Umo9Ye513"))
          (IF (not (dos_getcanceL)) (exit))
          (setq ldat1 (descompacta ldat1x))
          (IF (not (dos_getcanceL)) (exit))          
          (if (= procedencia "E")
            (progn
              (if (= controlbdace nil) (setq controlbdace 1))
              (setq cadenaprov (strcat estacion (itoa variable)))
              (setq valorx (list (cons 1 cadenaprov) (cons 2 ldat1)))
              (setq CONCATENADO (cons controlbdace valorx)) 
              (setq optimizadiarioe (append optimizadiarioe (list CONCATENADO)))
              (setq controlbdace (1+ controlbdace))
            )
          )
          (if (= procedencia "C")
            (progn
              (if (= controlbdacc nil) (setq controlbdacc 1))
              (setq cadenaprov (strcat estacion (itoa variable)))
              (setq valorx (list (cons 1 cadenaprov) (cons 2 ldat1)))
              (setq CONCATENADO (cons controlbdacC valorx)) 
              (setq optimizadiarioC (append optimizadiarioC (list CONCATENADO)))
              (setq controlbdacc (1+ controlbdacc))
            )
          )
          (dos_getcanceL t)
        )
      );if 
      (if (OR (= tipodat "AN") (= tipodat "ME") (= tipodat "MM"))
        (progn
          (if (= tipoproceso "MA") (setq ldat1 (maximos ldat1 tipodat variable fechaini)))
          (if (= tipoproceso "MI") (setq ldat1 (minimos ldat1 tipodat variable fechaini)))
          (if (= tipoproceso "ME") (setq ldat1 (media ldat1 tipodat variable fechaini)))
          (if (= tipoproceso "TO") (setq ldat1 (TOTALES ldat1 tipodat variable fechaini)))
          (if (= tipoproceso "VC") (setq ldat1 (PORCENTAJES ldat1 tipodat variable fechaini)))
          (if (AND (OR (= variable 1) (= variable 3)) (OR (= tipoproceso "MA") (= tipoproceso "MI") (= tipoproceso "ME")))
            (SETQ CARY 6)
          )
          (if (AND (OR (= variable 7) (= variable 8) (= variable 9)) (OR (= tipoproceso "MA") (= tipoproceso "MI") (= tipoproceso "ME")) )
            (SETQ CARY 5)
          )
          (if (= tipoproceso "TO")
            (SETQ CARY 9)
          )
          (if (= tipoproceso "VC")
            (SETQ CARY 5)
          )
          (if (and (or (= variable 2) (= variable 4) (= variable 5) (= variable 6)) (/= tipoproceso "VC"))
            (SETQ CARY 1)
          )
        )
      )
      (if (= tipodat "ST") (setq ldat1 (tempdiaria ldat1 variable fechaini)))
      (if (= tipodat "ST")
        (PROGN
          (SETQ CARX 6)
          (SETQ CARY ANCHOCHR)
        )
        (SETQ CARX 4)
      )
    )
  )
  (setq hfinx (escaneah))
  (if (> hfinx hfin) (setq hfin hfinx))
  (setq anchorealx (- (atoi (substr fechafin 1 4)) (atoi (substr fechaini 1 4))))
  (setq anchorealy (- hfin hini))
  (if (> anchorealx 1)
    (progn
      (setq sretpx (fix (/ (* 10 anchorealx) 100)))
      (setq sretsx (/ sretpx 6.0))
    )
    (progn
      (setq sretpx 1)
      (setq sretsx 0.083333)
    )
  )
  (setq sretpy (/ anchorealy 5.0))
  (setq sretsy (/ sretpy 2.0))
  (if (= lgui "S")
    (lineasgui 90 322 500 240 anchorealx anchorealy sretpx sretsx sretpy sretsy "SI" "SI" "SI" "SI" 251 251 251 251)
  )
  (graficax 500.000 240.000 NUMEROELEM anchorealy 90 82 1 hini ldat1 CARX CARY "NO" "NO" 1 (/ (strlen ldat1) (+ carx cary)) TIPO color "SI")
  (if (= cotas "S")
    (progn
      (acotagrf 90 82 500.000 anchorealx (atoi (substr fechaini 1 4)) sretpx sretsx 1 2 15 6 "SI" "NO" 7 7 3 1 8 8 "X" "romans" "romans" 3 3)
      (acotagrf 90 322 240.000 anchorealy hini sretpy sretsy 1 2 15 6 "SI" "NO" 7 7 3 1 8 8 "Y" "romans" "romans" 3 3)
    )
  )

  (SETQ ANCHOGRFVAL anchorealx)
  (SETQ FECHAINIGRF FECHAINI)
  (SETQ PRANGA1X (- RANGA1 90))
  (SETQ PRANGA2X (- RANGA2 90))
  (SETQ PRANGB1X (- RANGB1 90))
  (SETQ PRANGB2X (- RANGB2 90))
  (IF (= PRANGA1X 0)
    (SETQ PRANGA1X (+ (atoi (substr FECHAINI 1 4)) (* (atoi (substr FECHAINI 5 2)) 0.083333333)))
    (PROGN
      (SETQ DREALX (/ (* PRANGA1X ANCHOGRFVAL) 500.00))
      (SETQ PRANGA1X (+ (atoi (substr fechaINI 1 4)) DREALX))
    )
  )
  (IF (= PRANGB1X 0)
    (SETQ PRANGB1X (+ (atoi (substr FECHAINI 1 4)) (* (atoi (substr FECHAINI 5 2)) 0.083333333)))
    (PROGN
      (SETQ DREALX (/ (* PRANGB1X ANCHOGRFVAL) 500.00))
      (SETQ PRANGB1X (+ (atoi (substr fechaINI 1 4)) DREALX))
    )
  )
  (SETQ DREALX (/ (* PRANGA2X ANCHOGRFVAL) 500.00))
  (SETQ PRANGA2X (+ (atoi (substr fechaINI 1 4)) DREALX))
  (SETQ DREALX (/ (* PRANGB2X ANCHOGRFVAL) 500.00))
  (SETQ PRANGB2X (+ (atoi (substr fechaINI 1 4)) DREALX))
  (SETQ PRANGA1XM (- PRANGA1X (FIX PRANGA1X)))
  (SETQ PRANGA2XM (- PRANGA2X (FIX PRANGA2X)))
  (SETQ PRANGB1XM (- PRANGB1X (FIX PRANGB1X)))
  (SETQ PRANGB2XM (- PRANGB2X (FIX PRANGB2X)))
  (SETQ PRANGA1X (STRCAT (ITOA (FIX PRANGA1X)) (DEFINEMES PRANGA1XM) "01"))
  (SETQ PRANGA2X (STRCAT (ITOA (FIX PRANGA2X)) (DEFINEMES PRANGA2XM) "01"))
  (SETQ PRANGB1X (STRCAT (ITOA (FIX PRANGB1X)) (DEFINEMES PRANGB1XM) "01"))
  (SETQ PRANGB2X (STRCAT (ITOA (FIX PRANGB2X)) (DEFINEMES PRANGB2XM) "01"))
  (setq VARGRF2 (strcat (substr vargrf2 1 3) PRANGA1X PRANGA2X PRANGB1X PRANGB2X (substr vargrf2 36)))

  (if (and (= lgui "S") (= cotas "S"))
   (progn
    (if (AND (= variable 1) (/= tipoproceso "VC"))
      (progn
        (slide_image 25 90 60 220 (STRCAT RUTA "SLIDES\\detallesgrf(EVAP)"))
      )
    )
    (if (AND (= variable 3) (/= tipoproceso "VC"))
      (progn
        (slide_image 25 90 50 220 (STRCAT RUTA "SLIDES\\detallesgrf(HP)"))
      )
    )
    (if (AND (OR (= variable 7) (= variable 8) (= variable 9)) (/= tipoproceso "VC"))
      (progn
        (slide_image 25 90 48 200 (STRCAT RUTA "SLIDES\\detallesgrf(TEMP)"))
      )
    )
    (if (AND (OR (= variable 2) (= variable 4) (= variable 5) (= variable 6)) (/= tipoproceso "VC"))
      (progn
        (slide_image 25 125 20 110 (STRCAT RUTA "SLIDES\\detallesgrf(DIAS)"))
      )
    )
;    (if (/= tipodat "MM")
;      (slide_image 396 398 53 18 (STRCAT RUTA "SLIDES\\años"))
;    )
    (if (= tipoproceso "VC")
      (slide_image 25 90 40 180 (STRCAT RUTA "SLIDES\\detallesgrf(VACIOS)"))
    )
    (setq titulo1 "")
    (setq titulo2 "")
    (setq titulo3 "")
   )
  )
  (muestracl color 602 (+ 150 (* 18 (1- variable))) 24 4)
) 

(defun nombrevarclim ()
  (if (= variable 1) (setq resultado "Evap."))
  (if (= variable 2) (setq resultado "Gran."))
  (if (= variable 3) (setq resultado "Precip."))
  (if (= variable 4) (setq resultado "Neblina."))
  (if (= variable 5) (setq resultado "Cobert."))
  (if (= variable 6) (setq resultado "Torm."))
  (if (= variable 7) (setq resultado "Temp."))
  (if (= variable 8) (setq resultado "Temp mx"))
  (if (= variable 9) (setq resultado "Temp mi"))
  (setq resultado resultado)
)

(DEFUN DEFINEMES (SOBRANTE)
  (SETQ SOBRANTEN (/ SOBRANTE 0.083333333))
  (IF (< SOBRANTEN 1) (SETQ MESRST "01"))
  (IF (>= SOBRANTEN 1) 
    (IF (> SOBRANTEN 9)
      (SETQ MESRST (ITOA (1+ (FIX SOBRANTEN))))
      (SETQ MESRST (STRCAT "0" (ITOA (1+ (FIX SOBRANTEN)))))
    )
  )
  (SETQ MESRST MESRST)
);(DEFINEMES 0.81)
