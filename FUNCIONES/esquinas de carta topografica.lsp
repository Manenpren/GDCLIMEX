(DEFUN CARTAINGr (COORDENADA)
  (C:LIBRERIA "GEO-UTM")
  (SETQ LONGITUD (ATOF (RTOS (CAR COORDENADA) 2 12)))
  (SETQ LATITUD (ATOF (RTOS (CADR COORDENADA) 2 12)))
  (SETQ HUSO (FIX (+ (/ LONGITUD 6) 31)))
  (setq longx (* (fix (/ longitud 0.3333333333333)) 0.3333333333333))
  (setq latx (* (fix (/ latitud 0.25)) 0.25))
  (SETQ PGEO (LIST longx latx))
  (SETQ XYZ (GEO-UTM PGEO))
  (SETQ PGEO (LIST longx (+ latx 0.25)))
  (SETQ XYZ2 (GEO-UTM PGEO))
  (SETQ PGEO (LIST (- longx 0.3333333333333) (+ latx 0.25)))
  (SETQ XYZ3 (GEO-UTM PGEO))
  (SETQ PGEO (LIST (- longx 0.3333333333333) latx))
  (SETQ XYZ4 (GEO-UTM PGEO))
  (command "pline" xyz xyz2 xyz3 xyz4 "" "pedit" (entlast) "c" "")
)
