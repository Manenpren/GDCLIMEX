(defun AtrToList (blbus)
  (SETQ PR NIL)
  (SETQ PROB (TBLNEXT "BLOCK" T))
  (setq e (cdr (assoc -2 (TBLNEXT "BLOCK" T))))
  (setq tip (cdr (assoc 2 (TBLNEXT "BLOCK" T))))
  (WHILE (and PROB (= pr nil))
    (IF (= blbus tip) (SETQ PR "S"))
    (IF (/= blbus tip) 
      (PROGN
        (SETQ PROB (TBLNEXT "BLOCK"))
        (setq e (cdr (assoc -2 prob)))
        (setq tip (cdr (assoc 2 prob)))
      )
    )   
  )
  (setq datos nil)
  (setq datos2 nil)
  (setq noatri 1)
  (setq tpo (cdr (assoc 0 (entget e))))
  (WHILE (and E (/= tpo "ATTDEF"))
    (SETQ E (ENTNEXT E))
    (if (/= e nil)
      (setq tpo (cdr (assoc 0 (entget e))))
    )
  )
  (WHILE (and E (= tpo "ATTDEF"))
    (IF (= 1 NOATRI)
      (SETQ K 5)
    )
    (IF (= 2 NOATRI)
      (SETQ K 3)
    )
    (IF (= 3 NOATRI)
      (SETQ K 4)
    )
    (SETQ E2 (ENTGET E))
    (setq tpo (cdr (assoc 0 e2)))
    (setq nombre (cdr (assoc 3 e2)))
    (setq dato (cons nombre k))
    (setq datos (append datos (list dato)))
    (setq dato2 (cons noatri nombre))
    (setq datos2 (append datos2 (list dato2)))
    (SETQ E (ENTNEXT E))
    (setq noatri (1+ noatri))
  )
  (PRINT E2)
)
