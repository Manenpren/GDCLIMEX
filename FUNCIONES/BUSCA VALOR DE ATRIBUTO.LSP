(DEFUN BUSATR (E ATR)
 (SETQ E (ENTNEXT E))
 (SETQ R 0)
 (SETQ VALAT NIL)
 (WHILE (= "ATTRIB" (cdr (assoc 0 (entget E))))
   (if (= "ATTRIB" (cdr (assoc 0 (entget E))))
      (if (= ATR (cdr (assoc 2 (entget E))))
       (PROGN
        (setq vALAT (cdr (assoc 1 (entget E))))
       )
      )
   )
   (SETQ R (1+ R))
   (SETQ E (ENTNEXT E))
 )
 (PRINT ValAT)
)
