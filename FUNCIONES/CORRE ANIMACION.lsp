(DEFUN ANIM (textoesr xfuente xtamaño xins yins)
  (if (= nil Ddespfuente) 
    (progn
      (setq archIVOCL (open (strcat ruta "fuentes\\" xfuente ".fnt") "r"))
      (IF (= ARCHIVOCL NIL) (END))
      (setq lINEAfUENTE (read-line archIVOCL))
      (setq CONCATENADO (cons -1 xfuente)) 
      (setq Ddespfuente (append Ddespfuente (list CONCATENADO)))
      (setq CONCATENADO (cons 0 (atoi lineafuente))) 
      (setq Ddespfuente (append Ddespfuente (list CONCATENADO)))
      (setq xcont 1)
      (repeat 255
        (setq lINEAfUENTE (read-line archIVOCL))
        (setq CONCATENADO (cons xcont (atoi lineafuente))) 
        (setq Ddespfuente (append Ddespfuente (list CONCATENADO)))
        (setq xcont (1+ xcont))
      )
      (close archivocl)
    )
    (progn
      (setq cfnt (cdr (assoc -1 Ddespfuente)))
      (if (/= cfnt xfuente)
        (progn
          (setq archIVOCL (open (strcat ruta "fuentes\\" xfuente ".fnt") "r"))
          (IF (= ARCHIVOCL NIL) (END))
          (setq lINEAfUENTE (read-line archIVOCL))
          (setq CONCATENADO (cons -1 xfuente)) 
          (setq Ddespfuente (append Ddespfuente (list CONCATENADO)))
          (setq CONCATENADO (cons 0 (atoi lineafuente))) 
          (setq Ddespfuente (append Ddespfuente (list CONCATENADO)))
          (setq xcont 1)
          (repeat 255
            (setq lINEAfUENTE (read-line archIVOCL))
            (setq CONCATENADO (cons xcont (atoi lineafuente))) 
            (setq Ddespfuente (append Ddespfuente (list CONCATENADO)))
            (setq xcont (1+ xcont))
          )
          (close archivocl)
        )
      )
    )
  )
); (stexto textoesr "euroman" xtamaño xins yins)
