(DEFUN stextoj (textoesr xfuente xtamaño xins yins justificacion)
  (if (= nil Ddespfuente) 
    (progn
      (setq archIVOCL (open (strcat ruta "fuentes\\" xfuente ".fnt") "r"))
      (IF (= ARCHIVOCL NIL) (END))
      (setq lINEAfUENTE (read-line archIVOCL))
      (setq CONCATENADO (cons -1 xfuente)) 
      (setq Ddespfuente (append Ddespfuente (list CONCATENADO)))
      (setq CONCATENADO (cons 0 (atoi lineafuente))) 
      (setq Ddespfuente (append Ddespfuente (list CONCATENADO)))
      (setq xcont1 1)
      (repeat 255
        (setq lINEAfUENTE (read-line archIVOCL))
        (setq CONCATENADO (cons xcont1 (atoi lineafuente))) 
        (setq Ddespfuente (append Ddespfuente (list CONCATENADO)))
        (setq xcont1 (1+ xcont1))
      )
      (close archivocl)
    )
    (progn
      (setq cfnt (cdr (assoc -1 Ddespfuente)))
      (if (/= cfnt xfuente)
        (progn
          (setq archIVOCL (open (strcat ruta "fuentes\\" xfuente ".fnt") "r"))
          (IF (= ARCHIVOCL NIL) (END))
          (setq lINEAfUENTE (read-line archIVOCL))
          (setq CONCATENADO (cons -1 xfuente)) 
          (setq Ddespfuente (append Ddespfuente (list CONCATENADO)))
          (setq CONCATENADO (cons 0 (atoi lineafuente))) 
          (setq Ddespfuente (append Ddespfuente (list CONCATENADO)))
          (setq xcont1 1)
          (repeat 255
            (setq lINEAfUENTE (read-line archIVOCL))
            (setq CONCATENADO (cons xcont1 (atoi lineafuente))) 
            (setq Ddespfuente (append Ddespfuente (list CONCATENADO)))
            (setq xcont1 (1+ xcont1))
          )
          (close archivocl)
        )
      )
    )
  )
  (if (or (= justificacion "C") (= justificacion "D")) (setq yins (- yins xtamaño)))
  (setq xinsf 0)
  (if (or (= justificacion "B") (= justificacion "D")) 
    (progn
      (setq proporcion (/ (+ xtamaño 0.0000001) (+ hfuentex 0.0000001)))
      (SETQ LNGcad (STRLEN textoesr))
      (setq xcont1 1)
      (repeat lngcad
         (SETQ Ptext (SUBSTR textoesr xcont1 1))
         (setq espacioc (atoi (rtos (* proporcion (cdr (assoc (ascii ptext) Ddespfuente))) 2 0)))
         (setq xinsf (+ xinsf espacioc))
         (setq xcont1 (1+ xcont1))
      )
      (setq xins (- xins xinsf))
    )
  )
  (setq nomfnt (cdr (assoc -1 Ddespfuente)))
  (setq hfuentex (cdr (assoc 0 Ddespfuente)))
  (setq proporcion (/ (+ xtamaño 0.0000001) (+ hfuentex 0.0000001)))
  (SETQ LNGcad (STRLEN textoesr))
  (setq xcont1 1)
  (repeat lngcad
     (SETQ Ptext (SUBSTR textoesr xcont1 1))
     (setq espacioc (atoi (rtos (* proporcion (cdr (assoc (ascii ptext) Ddespfuente))) 2 0)))
     (slide_image xins yins espacioc xtamaño (STRCAT RUTA "fuentes\\" xfuente "(L" (itoa (ascii ptext)) ")"))
     (setq xins (+ xins espacioc))
     (setq xcont1 (1+ xcont1))
  )
); (stexto "textoesr" "euroman" xtamaño xins yins)
;justificaciones	"A" arriba-izquierda "B" arriba-derecha "C" Abajo-izquierda "D" Abajo-derecha
