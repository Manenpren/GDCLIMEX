(DEFUN NTOCAD (NUMERO NDECIMAL ANCHOF)
  (SETQ NUMERO (RTOS NUMERO 2 NDECIMAL))
  (IF (> (STRLEN NUMERO) ANCHOF) ())
  (SETQ DIFCAD (- ANCHOF (STRLEN NUMERO)))
  (SETQ DATOCOMP "")
  (REPEAT DIFCAD
    (SETQ DATOCOMP (STRCAT "0" DATOCOMP))
  )
  (if (= (substr numero 1 1) "-")
    (SETQ NUMERO (STRCAT "-" DATOCOMP (substr numero 2)))
    (SETQ NUMERO (STRCAT DATOCOMP NUMERO))
  )
  (setq numero numero)
)

;(NTOCAD 5.43512 3 10)
;NUMERO 	REAL-ENTERO		UN NUMERO REAL O ENTERO
;NDECIMAL	ENTERO		NUMERO DE DECIMALES A REPRESENTAR
;ANCHOF		ENTERO		ANCHO FINAL DEL NUMERO (EN CARACTERES)
