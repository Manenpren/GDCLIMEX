(DEFUN descompacta (cadenadesc)
  (setq anchocadenaf (strlen cadenadesc))
  (if (> anchocadenaf 5000)
    (dos_getprogress "Trabajando" "descompactando datos" anchocadenaf)
  )
  (setq cadenadsc "")
  (setq contdes 1)
  (setq charprv "x")
  (while (/= charprv "")
    (setq charprv (substr cadenadesc contdes 1))
    (if (and (> (ascii charprv) 47) (< (ascii charprv) 58))
      (progn
        (while (and (> (ascii charprv) 47) (< (ascii charprv) 58))
          (setq cadenacont charprv)
          (setq contdes (1+ contdes))
          (setq charprv (substr cadenadesc contdes 1))
          (while (and (> (ascii charprv) 47) (< (ascii charprv) 58))
            (setq cadenacont (strcat cadenacont charprv))
            (setq contdes (1+ contdes))
            (setq charprv (substr cadenadesc contdes 1))
          )
          (setq charprv (cambiacar charprv))
          (repeat (atoi cadenacont)
            (setq cadenadsc (strcat cadenadsc charprv))
          )
          (setq contdes (1+ contdes))
          (setq charprv (substr cadenadesc contdes 1))
        )
      )
    )
    (if (/= charprv "") 
      (progn
        (setq charprv (cambiacar charprv))
        (setq cadenadsc (strcat cadenadsc charprv))
      )
    )
    (if (> anchocadenaf 5000)
      (dos_getprogress contdes)
    )
    (setq contdes (1+ contdes))
  )
  (if (> anchocadenaf 5000)
    (dos_getprogress t)
  )
  (setq cadenadsc cadenadsc)
)

(defun cambiacar (caracter)
  (setq caracter2 "")
  (If (and (> (Ascii caracter) 96) (< (Ascii caracter) 107)) (setq caracter2 (Chr (- (Ascii caracter) 49))))
  (If (= "k" caracter) (setq caracter2 "x"))
  (If (= "l" caracter) (setq caracter2 "."))
  (If (= "m" caracter) (setq caracter2 "-"))
  (setq caracter2 caracter2)
)

;(setq ARCINSAT (open "d:\\prov.cli" "r"))
;(setq cadenaprv (READ-LINE arcinsat))
;(descompacta cadenaprv)
;(setq ARCINSAT (open "d:\\prov.txt" "w"))
;(WRITE-LINE gr ARCINSAT)
