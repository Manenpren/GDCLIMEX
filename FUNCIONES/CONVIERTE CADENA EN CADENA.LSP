(DEFUN CADTOCAD (CADENAFTE CARACTERr ANCHOF)
  (IF (> (STRLEN CADENAFTE) ANCHOF) ())
  (SETQ DIFCAD (- ANCHOF (STRLEN CADENAFTE)))
  (SETQ DATOCOMP "")
  (REPEAT DIFCAD
    (SETQ DATOCOMP (STRCAT CARACTERr DATOCOMP))
  )
  (SETQ CADENAFTE (STRCAT CADENAFTE DATOCOMP ))
)

;(NTOCAD 5.43512 3 10)
;CADENA 	CADENA		CADENA A CONVERTIR
;CARACTERr	CARACTER		CARACTER USADO PARA RELLENAR VALOR
;ANCHOF		ENTERO		ANCHO FINAL DE LA CADENA (EN CARACTERES)
