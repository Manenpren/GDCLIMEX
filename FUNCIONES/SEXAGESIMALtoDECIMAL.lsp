(DEFUN SEXADEC (DATO)
  (C:LIBRERIA "SEPARA VALORES DE ESPACIOS DE UN TEXTO TO LISTA2")
  (setq listado (SEPARA_VAL_SPC dato))
  (SETQ GRADOS (cdr (ASSOC 1 listado)))
  (SETQ MINUTOS (cdr (ASSOC 2 listado)))
  (SETQ SEGUNDOS (cdr (ASSOC 3 listado)))
  (setq total (rtos (+ (* (abs (atof grados)) 1.00000000) (/ (abs (atoi minutos)) 60.0000000000) (/ (/ (abs (atof segundos)) 60.0000000000) 60.0000000000)) 2 10))
  (if (> 0 (atof grados)) (setq total (strcat "-" total)) (setq total total))
)
