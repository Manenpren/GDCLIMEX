(defun directos (estacion procedencia variable)
;;  (if (< (atoi estacion) 9999)(setq estacion (strcat "0" (itoa(atoi estacion)))))
      (if (= procedencia "C")
        (progn
          (setq diradicional "CLICOM")
          (setq extencion ".cli")
        )
        (progn
          (setq diradicional "ERIC")
          (setq extencion ".clk")
        )
      )
      (if (= variable 1) (progn (setq dirprim "\\evapora\\") (setq ndec 2) (setq anchochr 6)))
      (if (= variable 2) (progn (setq dirprim "\\granizo\\") (setq ndec 0) (setq anchochr 1)))
      (if (= variable 3) (progn (setq dirprim "\\hp\\") (setq ndec 2) (setq anchochr 6)))
      (if (= variable 4) (progn (setq dirprim "\\neblina\\") (setq ndec 0) (setq anchochr 1)))
      (if (= variable 5) (progn (setq dirprim "\\nublado\\") (setq ndec 0) (setq anchochr 1)))
      (if (= variable 6) (progn (setq dirprim "\\rayos\\") (setq ndec 0) (setq anchochr 1)))
      (if (= variable 7) (progn (setq dirprim "\\temp\\") (setq ndec 2) (setq anchochr 5)))
      (if (= variable 8) (progn (setq dirprim "\\tempmax\\") (setq ndec 2) (setq anchochr 5)))
      (if (= variable 9) (progn (setq dirprim "\\tempmin\\") (setq ndec 2) (setq anchochr 5)))
      (setq ldat1 "")
      (if (and (= procedencia "E") (/= optimizadiarioe nil)) (setq ldat1 (optimizabdiarios2 estacion variable)))
      (if (and (= procedencia "C") (/= optimizadiarioc nil)) (setq ldat1 (optimizabdiarios2 estacion variable)))
      (if (= ldat1 "")
        (progn      
          (dos_getcancel "LEYENDO BD" "LEYENDO DATOS POR FAVOR ESPERE...")
          (IF (not (dos_getcanceL)) (exit))
          (dos_encrypt (strcat ruta "BASES DE DATOS\\DATOS CLIMATOLOGICOS\\" diradicional dirprim estacion extencion) (strcat "4avEjsD8GlñOpwrpfvc3071fdA" estacion "Ga4TykP8G5Umo9Ye513"))
          (setq archIVOindice (open (strcat ruta "BASES DE DATOS\\DATOS CLIMATOLOGICOS\\" diradicional dirprim estacion extencion) "r"))
          (setq ldat1x (read-line archIVOindice))
          (close archivoindice)
          (dos_encrypt (strcat ruta "BASES DE DATOS\\DATOS CLIMATOLOGICOS\\" diradicional dirprim estacion extencion) (strcat "4avEjsD8GlñOpwrpfvc3071fdA" estacion "Ga4TykP8G5Umo9Ye513"))
          (dos_getcanceL t)
          (setq ldat1 (descompacta ldat1x))
          (if (= procedencia "E")
            (progn
              (if (= controlbdace nil) (setq controlbdace 1))
              (setq cadenaprov (strcat estacion (itoa variable)))
              (setq valorx (list (cons 1 cadenaprov) (cons 2 ldat1)))
              (setq CONCATENADO (cons controlbdace valorx)) 
              (setq optimizadiarioe (append optimizadiarioe (list CONCATENADO)))
              (setq controlbdace (1+ controlbdace))
            )
          )
          (if (= procedencia "C")
            (progn
              (if (= controlbdacc nil) (setq controlbdacc 1))
              (setq cadenaprov (strcat estacion (itoa variable)))
              (setq valorx (list (cons 1 cadenaprov) (cons 2 ldat1)))
              (setq CONCATENADO (cons controlbdacC valorx)) 
              (setq optimizadiarioC (append optimizadiarioC (list CONCATENADO)))
              (setq controlbdacc (1+ controlbdacc))
            )
          )
        )
      );if 
  (setq ldat1 ldat1)
)

(defun optimizabdiarios2 (estacion variable)
  (if (= procedencia "C")
    (progn
      (setq contcig 1)
      (setq estaciong "000000")
      (setq scierto "")
      (while (and (or (/= estacion (substr estaciong 1 5)) (/= VARIABLE (ATOI (substr estaciong 6 1)))) (< contcig controlbdacc))
        (setq estaciong (cdr (car (cdr (assoc contcig optimizadiarioc)))))
        (if (and (= estacion (substr estaciong 1 5)) (= VARIABLE (ATOI (substr estaciong 6 1)))) (setq scierto "s"))
        (setq contcig (1+ contcig))
      )
      (IF (= scierto "s")
        (setq listadat (cdr (cadr (cdr (assoc (1- contcig) optimizadiarioc)))))
        (setq listadat "")
      )
    )
    (progn
      (setq contcig 1)
      (setq estaciong "000000")
      (setq scierto "")
      (while (and (or (/= estacion (substr estaciong 1 5)) (/= VARIABLE (ATOI (substr estaciong 6 1)))) (< contcig controlbdacE))
        (setq estaciong (cdr (car (cdr (assoc contcig optimizadiarioe)))))
        (if (and (= estacion (substr estaciong 1 5)) (= VARIABLE (ATOI (substr estaciong 6 1)))) (setq scierto "s"))
        (setq contcig (1+ contcig))
      )
      (IF (= scierto "s")
        (setq listadat (cdr (cadr (cdr (assoc (1- contcig) optimizadiarioe)))))
        (setq listadat "")
      )
    )
  )
  (setq listadat listadat)
)

;(leebd "16087" "C" 3 "190001" "ST" "")
;estacion	cadena		estacion a graficar
;procedencia	cadena		Clicom o erick
;variable	entero		variable climatica a graficar 1-9
;FECHAINI	CADENA		FECHA INICIAL A PROCESAR LOS DATOS DE LA GRAFICA formato de 4 6 o 8 caracteres segun se requiera
;tipodat	CADENA		tipo de datos a graficar "AN" "ME" "ST" "MM"
;tipoproceso	cadena		tipo de proceso a recibir la cadena (valores maximos, minimos, medios, totales, %vacios, serie temporal) "MA" "MI" "ME" "TO" "VC" "ST"
