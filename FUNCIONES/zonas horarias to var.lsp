(defun zhvar ()
  (C:LIBRERIA "SEPARA VALORES DE COMAS DE UN TEXTO TO LISTA")
  (setq archdim (open (strcat ruta "bases de datos\\zutmp.CSV") "r"))
  (setq lINEAfUENTE (read-line archdim))
  (setq nver 0)
  (setq salir "N")
  (SETQ matrizpol NIL)
  (while lineafuente /= ""
    (setq lineafuente (SEPARA_VAL_COMAS lineafuente))
    (setq CONCATENADO (cons nver (list (cdr (assoc 1 lineafuente)) (cdr (assoc 2 lineafuente)) (cdr (assoc 4 lineafuente)))))
    (setq matrizpol (append matrizpol (list CONCATENADO)))
    (setq nver (+ nver 1))
    (setq lINEAfUENTE (read-line archdim))
  )
  (close archdim)
  (setq matrizpol matrizpol)
)
