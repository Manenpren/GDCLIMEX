(defun correlacionv (Listaestac procedencia variable fechaini tipodat tipoproceso) 
  (C:LIBRERIA "correlacionr")
  (C:LIBRERIA "lee datos estacion")
  (C:LIBRERIA "encuentra coincidencias")
  (if (= variable 1) (setq anchochr 6))
  (if (= variable 2) (setq anchochr 1))
  (if (= variable 3) (setq anchochr 6))
  (if (= variable 4) (setq anchochr 1))
  (if (= variable 5) (setq anchochr 1))
  (if (= variable 6) (setq anchochr 1))
  (if (= variable 7) (setq anchochr 5))
  (if (= variable 8) (setq anchochr 5))
  (if (= variable 9) (setq anchochr 5))
          (if (AND (OR (= variable 1) (= variable 3)) (OR (= tipoproceso "MA") (= tipoproceso "MI") (= tipoproceso "ME")))
            (SETQ CARY 6)
           )
          (if (AND (OR (= variable 7) (= variable 8) (= variable 9)) (OR (= tipoproceso "MA") (= tipoproceso "MI") (= tipoproceso "ME")) )
            (SETQ CARY 5)
          )
          (if (= tipoproceso "TO")
           (SETQ CARY 9)
          )
          (if (= tipoproceso "VC")
           (SETQ CARY 5)
          )
          (if (and (or (= variable 2) (= variable 4) (= variable 5) (= variable 6)) (/= tipoproceso "VC"))
            (SETQ CARY 1)
          )
          (if (= tipodat "ST") (setq carx 6))
          (if (/= tipodat "ST") (setq carx 4))
  (setq nestaccx (/ (strlen listaestac) 6))
  (setq cont1 1)
  (SETQ COEFCORREL "")
  (setq bdestacc nil)
  (repeat nestaccx
    (SETQ ESTACION (SUBSTR LISTAESTAC (1+ (* (1- CONT1) 6)) 5))
    (SETQ procedencia (SUBSTR LISTAESTAC (+ 6 (* (1- CONT1) 6)) 1))
    (setq datoex (leebd estacion procedencia variable fechaini tipodat tipoproceso))
    (setq valorx (list (cons 1 ESTACION) (cons 2 DATOEX)))
    (setq CONCATENADO (cons cont1 valorx)) 
    (setq BDESTACC (append BDESTACC (list CONCATENADO)))
    (SETQ CONT1 (1+ CONT1))
  )
  (setq cont1 NESTACCx)
  (setq listacorrelaini "")
  (repeat (1- NESTACCx)
    (setq varprv (ASSOC CONT1 BDESTACC))
    (setq cont3 1)
    (repeat (1- cont1)
      (setq varprv2 (ASSOC CONT3 BDESTACC))
      (setq varprvF (coincidencias (CDR (ASSOC 2 (CDR varprv))) (CDR (ASSOC 2 (CDR varprv2))) carx cary))
      (setq ndat (/ (/ (strlen varprvF) (+ carx cary)) 2))
      (setq varprvx (substr varprvF 1 (/ (strlen varprvF) 2)))
      (setq varprvx2 (substr varprvF (1+ (/ (strlen varprvF) 2))))
      (if (/= varprvx "")
        (progn
          (setq correlacion (correlacionr varprvx varprvx2 carx cary))
        )
        (setq correlacion 0.00)
      )
      (SETQ COEFCORREL (STRCAT COEFCORREL (SUBSTR LISTAESTAC (1+ (* (1- CONT3) 6)) 6) (SUBSTR LISTAESTAC (1+ (* (1- CONT1) 6)) 6) (ntocad CORRELACION 5 8)))
      (setq listacorrelaini (strcat listacorrelaini ))
      (setq cont3 (1+ cont3))
    )
    (setq cont1 (1- cont1))
  )
  (SETQ COEFCORREL COEFCORREL)
)

(defun correlacionarch (cadenacorrela archivoesc)
  (setq nestaccx (/ (strlen cadenacorrela) 20))
  (setq cont1 1)
  (setq archivo (open archivoesc "w"))
  (repeat nestaccx
    (SETQ lineaex (SUBSTR cadenacorrela (1+ (* (1- CONT1) 20)) 20))
    (WRITE-LINE LINEAex ARCHIvo)    
    (SETQ CONT1 (1+ CONT1))
  )
  (close archivo)
)

;(correlacionv "16006160071601216014160151604716056160741608216087160881611816123161271613316142161461614716164161651617116188" "C" 3 "190001" "ST" "")
;(correlacionv "16001C16010C16049C16087C16109C16123C16133C16139C16140C16146C16168C16187C16257C16512C16001E16010E16049E16087E16109E16123E16133E16139E16140E16146E16168E16187E16257E16512E" "C" 3 "19000101" "ME" "MA")
;(correlacionarch (correlacionv "16006C16007C16012C16015C16047C16056C16074C16082C16087C16088C16089C16118C16123C16127C16133C16142C16146C16147C16164C16165C16171C16188C" "C" 3 "19000101" "ME" "MA") "C:\\descarga.txt")
;(correlacionarch resultadocorr "C:\\descarga.txt")
;(setq matrizcorrelaf (generamatrizc resultadocorr NCORRELA nestactbl))
