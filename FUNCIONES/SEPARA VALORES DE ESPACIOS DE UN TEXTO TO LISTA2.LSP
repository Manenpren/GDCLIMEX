(DEFUN SEPARA_VAL_SPC (TEXTOF)
  (SETQ CARX (SUBSTR TEXTOF 1 1))
  (setq contadorx 1)
  (while (= carx " ")
    (SETQ CARX (SUBSTR TEXTOF contadorx 1))
    (setq contadorx (1+ contadorx))
  )
  (SETQ ListaDatos NIL)
  (SETQ CONTVAR 1)
  (SETQ PUNTERO (1- contadorx))
  (SETQ INIVAR contadorx)
  (SETQ CADENAVAL "")
  (WHILE (/= CARX "")
    (IF (= CARX " ")
      (PROGN
        (setq contadorx 0)
        (while (= carx " ")
          (SETQ PUNTERO (1+ PUNTERO))
          (setq contadorx (1+ contadorx))
          (SETQ CARX (SUBSTR TEXTOF puntero 1))
        )
        (setq puntero (1- puntero))
;        (ALERT (RTOS CONTADORX))
        (SETQ CADENAVAL (SUBSTR TEXTOF INIVAR (- PUNTERO INIVAR (1- contadorx))))
        (setq CONCATCADENA (cons CONTVAR CADENAVAL))
        (setq ListaDatos (append ListaDatos (list CONCATCADENA)))
        (SETQ CONTVAR (1+  CONTVAR))
        (SETQ INIVAR (1+  PUNTERO))
      )
    )
    (SETQ PUNTERO (1+ PUNTERO))
    (SETQ CARX (SUBSTR TEXTOF PUNTERO 1))
  )
  (SETQ CADENAVAL (SUBSTR TEXTOF INIVAR (- PUNTERO INIVAR)))
  (setq CONCATCADENA (cons CONTVAR CADENAVAL))
  (setq ListaDatos (append ListaDatos (list CONCATCADENA)))
)
