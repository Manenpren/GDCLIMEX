(DEFUN graficax (ax ay realx realy cx cy crx cry tablagrf anchox anchoy vajustx vajusty varini ndatgrf tipogrf colores degradado)
  (dos_waitcursor t)
  (if (= strlen colores 3) (setq degradado "NO"))
  (dos_getprogress "Mensaje" "Graficando" (- ndatgrf VARINI))
  (C:LIBRERIA "tranforma coordenadas dibujo im dconcatenados")
  (setq contgrf 0)
;  (setq realx (+ realx 2))
 ; (setq cy (atoi(+ cy  (/ realx ax))))
  (if (or (= degradado "SI") (= vajustx "SI") (= vajusty "SI"))
    (progn 
      (setq mingrfx nil)
      (setq mingrfy nil)
      (setq maxgrfx nil)
      (setq maxgrfy nil)
      (setq ndatgrfx (- (/ (strlen tablagrf) (+ anchox anchoy)) (- varini 1)))
      (repeat ndatgrfx
        (setq datextx (substr tablagrf (1+ (* contgrf (+ anchox anchoy))) anchox))
        (setq datexty (substr tablagrf (1+ (+ (* contgrf (+ anchox anchoy)) anchox)) anchoy))
        (if (= contgrf 1)
          (progn
	    (setq mingrfx datextx)
            (setq mingrfy datexty)
            (setq maxgrfx datextx)
            (setq maxgrfy datexty)
	  )
        )
        (if (> datextx maxgrfx) (setq maxgrfx datextx))
        (if (< datextx mingrfx) (setq mingrfx datextx))
        (if (> datexty maxgrfy) (setq maxgrfy datexty))
        (if (< datexty mingrfy) (setq mingrfy datexty))
        (setq contgrf (1+ contgrf))
      )
    )
  )
  (setq cprovx nil)
  (setq cprovx2 nil)
  (setq cprovx3 nil)
  (setq cprovx4 nil)
  (setq cprovy nil)
  (setq cprovy2 nil)
  (setq cprovy3 nil)
  (setq cprovy4 nil)
  (if (= vajustx "SI")
    (progn
      (setq cprovx (/ (- maxgrfx mingrfx) ax))
      (if (>= cprovx 1)
        (progn
          (setq cprovx2 (- cprovx (fix cprovx)))
        )
        (progn
          (setq cprovx3 (/ ax (- maxgrfx mingrfx)))
          (setq cprovx4 (- cprovx3 (fix cprovx3)))
        )
      )
      (setq realx (- maxgrfx mingrfx))
      (setq ndatgrf (- (/ (strlen tablagrf) (+ anchox anchoy)) (- varini 1)))
    )
  )
  (if (= vajusty "SI")
    (progn
      (setq cprovy (/ (- (atof maxgrfy) (atof mingrfy)) ay))
      (if (>= cprovy 1)
        (progn
          (setq cprovy2 (- cprovy (fix cprovy)))
        )
        (progn
          (setq cprovy3 (/ ay (- maxgrfy mingrfy)))
          (setq cprovy4 (- cprovy3 (fix cprovy3)))
        )
      )
      (setq realy (- maxgrfy mingrfy))
    )
  )
  (if (> realx ax) 
    (progn
      (setq nresumen (/ realx ax))
      (setq dresumen (- nresumen (fix nresumen)))
      (setq nresumen (1+ (fix nresumen)))
      (setq tablagrfprov "")
      (setq contreal varini)
      (repeat (fix ax)
        (setq contresumen 1)
        (setq yresumen 0)
        (setq prvx "")
        (repeat nresumen
          (setq listay (atof (substr tablagrf (1+ (+ (* contreal (+ anchox anchoy)) anchox)) anchoy)))
          (setq yresumen (+ listay yresumen))
          (setq contreal (1+ contreal))
          (setq contresumen (1+ contresumen))
        )
        (setq yresumen (/ yresumen nresumen))
;        (setq prvx (itoa contreal))
;        (if (< contreal 10) (setq prvx (strcat "000" prvx)))
;        (if (and (> contreal 9) (< contreal 100)) (setq prvx (strcat "00" prvx)))
;        (if (and (> contreal 99) (< contreal 1000)) (setq prvx (strcat "0" prvx)))
        (setq prvx (ntocad contreal 0 anchox))
;        (setq anchox 3)
;        (setq prvy (rtos yresumen 2 0))
        (setq prvy (ntocad yresumen 0 anchoy))
;        (if (< (strlen prvy) anchoy)
;          (if (= (strlen prvy) (1- anchoy))
;            (setq prvy (strcat "0" prvy))
;            (if (= (strlen prvy) (- anchoy 2))
;              (setq prvy (strcat "00" prvy))
;              (if (= (strlen prvy) (- anchoy 3))
;                (setq prvy (strcat "000" prvy))
;                (if (= (strlen prvy) (- anchoy 4))
;                  (setq prvy (strcat "0000" prvy))
;                  (if (= (strlen prvy) (- anchoy 5))
;                    (setq prvy (strcat "00000" prvy))
;                  )
;                )
;              )
;            )
;          )
;        )

        (setq tablagrfprov (strcat tablagrfprov prvx prvy))
        (setq contreal (1- contreal))
      )
      (setq varini 1)
      (setq ndatgrf (fix ax))
      (setq tablagrf tablagrfprov)
    )
  )
;  (print tablagrf)
  (SETQ MATRIZDIBUgrf (TRFCOR2 tablagrf ax ay crx cry (+ crx realx) (+ cry realy) cx cy anchox anchoy))
  (if (= degradado "SI")
    (setq intervalodeg (/ ay (/ (strlen colores) 3)))
    (progn
       (setq intervalodeg nil)
      (setq colorprv colores)
    )
  )
  (setq contgrf varini)
  (setq datextx 0)
  (if (= tipogrf "DS")
    (WHILE (and (>= ndatgrf contgrf) (>= (+ AX CX) DATEXTX))
      (setq verpolgrf (cdr (assoc contgrf MATRIZDIBUgrf)))
      (setq datextx (car verpolgrf))
      (setq datexty (cadr verpolgrf))
      (if (= degradado "SI")
        (setq colorprv (dcolor (- (+ cy ay) datexty)))
      )
      (if (= colorprv "") (setq colorprv (substr colores (- (strlen colores) 2) 3)))
      (vector_image (atoi (rtos datextx 2 0)) (atoi (rtos datexty 2 0)) (atoi (rtos datextx 2 0)) (atoi (rtos datexty 2 0)) (atoi colorprv))
      (dos_getprogress contgrf)
      (setq contgrf (1+ contgrf))
    )
  )
  (if (= tipogrf "BR")
    (progn
      (setq anchobr (fix (/ ax realx)))
      (if (< anchobr 1) (setq anchobr 1))
      (WHILE (and (>= ndatgrf contgrf) (>= (+ AX CX) DATEXTX))
        (setq verpolgrf (cdr (assoc contgrf MATRIZDIBUgrf)))
        (setq datextx (car verpolgrf))
        (setq datexty (cadr verpolgrf))
        (if (= degradado "SI")
          (setq colorprv (dcolor (- (+ cy ay) datexty)))
        )
        (if (= colorprv "") (setq colorprv (substr colores (- (strlen colores) 2) 3)))
        (fill_image (- (atoi (rtos datextx 2 0)) (/ anchobr 2)) (atoi (rtos (+ cy ay) 2 0)) anchobr (atoi (rtos (- datexty (+ cy ay)) 2 0)) (atoi colorprv))
        (dos_getprogress contgrf)
        (setq contgrf (1+ contgrf))
      )
    )
  )
  (setq contgrf 1)
  (if (= tipogrf "LI")
    (progn
      (WHILE (and (>= ndatgrf contgrf) (>= (+ AX CX) DATEXTX))
        (setq verpolgrf (cdr (assoc contgrf MATRIZDIBUgrf)))
        (setq datextx (car verpolgrf))
        (setq datexty (cadr verpolgrf))
        (if (= degradado "SI")
          (setq colorprv (dcolor (- (+ cy ay) datexty)))
        )
        (if (= colorprv "") (setq colorprv (substr colores (- (strlen colores) 2) 3)))
        (if (> contgrf 1)
          (vector_image (atoi (rtos datextx2 2 0)) (atoi (rtos datexty2 2 0)) (atoi (rtos datextx 2 0)) (atoi (rtos datexty 2 0)) (atoi colorprv))
        )
        (dos_getprogress contgrf)
        (setq contgrf (1+ contgrf))
	(setq verpolgrf2 verpolgrf)
        (setq datextx2 datextx)
        (setq datexty2 datexty)
      )
    )
  )
  (dos_getprogress t)
  (setq contgrf nil)
  (dos_waitcursor)
)

(defun dcolor (elev)
  (setq vprovd (/ elev intervalodeg))
  (setq vprovd (1+ (* 3 (fix vprovd))))
  (setq vprovd (substr colores vprovd 3))
)

;        (fill_image 0 0 width height 0)   
;          (vector_image 40 180 560 180 (atoi cret)) 

;ax	entero		ancho de la grafica
;ay	entero
;realx	real		ancho real de la grafica en caso de realx siempre va de 1 en 1 
;realy	real
;'cx	entero		coordenada inicial para graficar superior izquierda
;cy	entero
;crx	real		coordenada inicial del punto de partida de la grafica en coordenadas reales inferior izquierda
;cry	real
;tablagrf	cadena		listado de datos a graficar
;anchox		entero		ancho de los caracteres
;anchoy		entero
;vajustx	cadena		ajustar el ancho de la grafica SI o NO
;vajusty	cadena
;varini		entero		numero de dato a empezar a graficar
;ndatgrf        entero          numero de datos a graficar
;tipogrf	cadena		tipo de grafico "dispersion, barras o linea continua(DS,BR,LI)"
;colores	cadena		si degradado no colores= 1 color lo contrario colores = "color...color5" donde color 3 caracteres   azules "007131141140142152154164166176178" rojos "051041040030032022024014016018"  morados "007241231221211201191190192194196198"
;degradado	cadena		degradado SI o NO
