(DEFUN CENTRPOL (POL)
  (C:LIBRERIA "VERTICES DE UNA LWPOLYLINE")
  (C:LIBRERIA "ENCUENTRA SENTIDO POLILINEA")
  (SETQ entpolilinea NIL)
  (SETQ P1T (VERTICE POL 1))
  (SETQ XMENOR (CAR P1T))
  (SETQ YMENOR (CADR P1T))
  (SETQ XMAYOR XMENOR)
  (SETQ YMAYOR YMENOR)
  (SETQ PROVV P1T)
  (setq prov 2)
  (while p1t
    (SETQ X2PROV (CAR P1T))
    (SETQ Y2PROV (CADR P1T))
    (IF (AND (< X2PROV XMENOR) (/= X2PROV nil)) (SETQ XMENOR X2PROV))
    (IF (AND (< Y2PROV YMENOR) (/= Y2PROV nil)) (SETQ YMENOR Y2PROV))
    (IF (AND (> X2PROV XMAYOR) (/= X2PROV nil)) (SETQ XMAYOR X2PROV))
    (IF (AND (> Y2PROV YMAYOR) (/= Y2PROV nil)) (SETQ YMAYOR Y2PROV))
    (SETQ PROV (1+ PROV))
    (SETQ P1T (VERTICE POL PROV))
  )
  (setq dosx (* (- xmayor xmenor) 0.15))
  (setq dosy (* (- ymayor ymenor) 0.15))
  (COMMAND "ZOOM" "W" (STRCAT (RTOS (- XMENOR dosx) 2 6) "," (RTOS (- YMENOR dosy) 2 6)) (STRCAT (RTOS (+ XMAYOR dosx) 2 6) "," (RTOS (+ YMAYOR dosy) 2 6)))
  (REDRAW POL 1)
  (SETQ RES (SENTPOL POL))
  (IF (= RES "ANTIHORARIO")
    (PROGN
      (setq f 0)
      (SETQ VERY "")
      (while verY
         (setq f (1+ f))
         (SETQ VERY (vertice POL f)) 
      )
      (COMMAND "PLINE")
      (setq f (1- f))
      (SETQ VERY (vertice POL f)) 
      (while verY
         (IF (and (/= VERY NIL) (/= very verx))
            (COMMAND VERY)  
         )
         (setq f (1- f))
         (setq verx very)
         (SETQ VERY (vertice POL f)) 
      )
      (COMMAND "C")
      (SETQ POL (ENTLAST))
    )
  )
  (SETQ CONT1 1)
  (SETQ VERTX1 (VERTICE POL CONT1))
  (SETQ CONT1 2)
  (COMMAND "AREA" "E" POL)
  (SETQ AREAP (GETVAR "AREA"))
  (SETQ SUMATORIAX 0)
  (SETQ SUMATORIAY 0)
  (WHILE VERTX1
    (SETQ VERTX2 VERTX1)
    (SETQ VERTX1 (VERTICE POL CONT1))
    (IF (/= VERTX1 NIL)
      (PROGN
        (SETQ IX1 (- (CAR VERTX2) xmenor))
        (SETQ IY1 (- (CADR VERTX2) ymenor))
        (SETQ IX2 (- (CAR VERTX1) xmenor))
        (SETQ IY2 (- (CADR VERTX1) ymenor))
        (SETQ SUMATORIAX (+ SUMATORIAX (abs (/ (* (+ ix1 ix2) (- (* ix1 iy2) (* ix2 iy1))) (* 6 AREAP)))))
        (SETQ SUMATORIAY (+ SUMATORIAY (abs (/ (* (+ iy1 iy2) (- (* ix1 iy2) (* ix2 iy1))) (* 6 AREAP)))))
;        (SETQ SUMATORIAX (+ SUMATORIAX (abs (/ (* (- IY1 IY2) (+ (* 2 IX1) (* IX1 IX2) (* IX2 2))) (* 6 AREAP)))))
;        (SETQ SUMATORIAY (+ SUMATORIAY (abs (/ (* (- IX2 IX1) (+ (* 2 IY1) (* IY1 IY2) (* IY2 2))) (* 6 AREAP)))))
      )
    )
    (SETQ CONT1 (1+ CONT1))
  );WHILE
  (SETQ VERTX1 (VERTICE POL 1))
  (SETQ IX1 (- (CAR VERTX2) xmenor))
  (SETQ IY1 (- (CADR VERTX2) ymenor))
  (SETQ IX2 (- (CAR VERTX1) xmenor))
  (SETQ IY2 (- (CADR VERTX1) ymenor))
  (SETQ SUMATORIAX (+ SUMATORIAX (abs (/ (* (+ ix1 ix2) (- (* ix1 iy2) (* ix2 iy1))) (* 6 AREAP)))))
  (SETQ SUMATORIAY (+ SUMATORIAY (abs (/ (* (+ iy1 iy2) (- (* ix1 iy2) (* ix2 iy1))) (* 6 AREAP)))))
  (SETQ SUMATORIAX (+ SUMATORIAX (abs (/ (* (- IY1 IY2) (+ (* 2 IX1) (* IX1 IX2) (* IX2 2))) (* 6 AREAP)))))
  (SETQ SUMATORIAY (+ SUMATORIAY (abs (/ (* (- IX2 IX1) (+ (* 2 IY1) (* IY1 IY2) (* IY2 2))) (* 6 AREAP)))))
  (setq sumatoriax (+ sumatoriax xmenor))
  (setq sumatoriay (+ sumatoriay ymenor))
  (SETQ CENTROIDE (LIST 10 SUMATORIAX SUMATORIAY 0))
;  (ENTMAKE (LIST '(0 . "POINT") '(8 . "0") CENTROIDE))
)
