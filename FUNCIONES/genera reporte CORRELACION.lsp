(DEFUN greportC (LISTAcorrelaciones)
  (desactiva3 "PR1")
  (desactiva3 "PR2")
  (desactiva3 "PR3")
  (desactiva3 "DATOSF1")
  (desactiva3 "DATOSF2")
  (desactiva3 "DATOSF3")
  (desactiva3 "DATOSF4")
  (desactiva3 "DATOSF5")
  (desactiva2 "mapa")
  (desactiva3 "SEL1")
  (fill_image 143 0 631 624 31)
  (fill_image 152 9 480 480 105)
  (fill_image 638 7 132 22 105)  
  (fill_image 644 33 40 16 7)  
  (fill_image 644 56 40 16 140)  
  (fill_image 644 79 40 16 100)  
  (fill_image 644 102 40 16 50)  
  (fill_image 644 125 40 16 42)
  (fill_image 644 148 40 16 30)
  (fill_image 644 171 40 16 1)
  (fill_image 644 194 40 16 6)
  (setq slidexx "BTN2(CORRELA)")
  (slide_image 143 -4 633 626 (STRCAT RUTA "SLIDES\\" slidexx ".SLD"))
  (activa2 "CORREPORTE")
  (SETQ NCORRELA (/ (STRLEN LISTAcorrelaciones) 20))
  (setq nestactbl (nestaciones ncorrela))
  (SETQ ANCHOCUAD (/ 480 nestactbl))
  (IF (> ANCHOCUAD 50) (SETQ ANCHOCUAD 50))
  (SETQ LISTADCLOBJ (MBDDCL2 LISTADCLOBJ "A" 152 9 (+ 152 (* ANCHOCUAD nestactbl)) (+ 9 (* ANCHOCUAD nestactbl)) "CORRELACIONOBJ" "X" "0" "x" "x" "x" "" "0" "0" ""))
  (setq contcol 1)
  (setq nivelp nestactbl)
  (setq sumaprv nestactbl)
  (REPEAT ncorrela
    (if (= sumaprv 1)
      (progn 
        (setq nivelp (1- nivelp))
        (setq sumaprv (1- nivelp))
      )
      (setq sumaprv (1- sumaprv))
    )
    (setq valorindiv (substr LISTAcorrelaciones (1+ (* 20 (1- contcol))) 20))
    (setq colorrec (dcolor2 (atof (substr valorindiv 13 8))))
    (fill_image (+ 152 (* (- nivelp sumaprv 1) anchocuad)) (+ 9 (* (1- nivelp) anchocuad)) ANCHOCUAD ANCHOCUAD colorrec)
    (fill_image (+ 152 (* (1- nivelp) anchocuad)) (+ 9 (* (- nivelp sumaprv 1) anchocuad)) ANCHOCUAD ANCHOCUAD colorrec)
    (setq contcol (1+ contcol))
  )
  (setq contbl 0)
  (repeat nestactbl
    (fill_image (+ 152 (* contbl anchocuad)) (+ 9 (* contbl anchocuad)) ANCHOCUAD ANCHOCUAD 7)
    (setq contbl (1+ contbl))
  )
  (SETQ OBJETO (BUSOBJBD LISTADCLOBJ 74 "EXCELC1"))
  (dibujaelem OBJETO)
  (SETQ OBJETO (BUSOBJBD LISTADCLOBJ 74 "SALIRC1"))
  (dibujaelem OBJETO)
;  (SETQ LISTADCLOBJ (MBDDCL2 LISTADCLOBJ "A" 152 9 (* nestactbl anchocuad) (* nestactbl anchocuad) "MATRIZCORRELA" "A" "0" "" "" "" "" "0" "0" ""))
  (setq matrizcorrelaf (generamatrizc LISTAcorrelaciones NCORRELA nestactbl))
)

(defun dcolor2 (elev)
  (setq resultado "")
  (setq elev (abs elev))
  (if (= elev 1) (setq resultado 7))
  (if (and (< elev 1) (>= elev 0.95)) (setq resultado 140))
  (if (and (< elev 0.95) (>= elev 0.9)) (setq resultado 100))
  (if (and (< elev 0.9) (>= elev 0.8)) (setq resultado 50))
  (if (and (< elev 0.8) (>= elev 0.7)) (setq resultado 42))
  (if (and (< elev 0.7) (>= elev 0.5)) (setq resultado 30))
  (if (and (< elev 0.5) (>= elev 0.25)) (setq resultado 1))
  (if (and (< elev 0.25) (>= elev 0.0)) (setq resultado 6))
  (setq resultado resultado)
)

(defun nestaciones (ncorrelac)
  (setq contestn 1)
  (setq varprvn 2)
  (while (AND (/= varprvn ncorrelac) (> NCORRELAC CONTESTN))
    (setq contestn (1+ contestn))
    (IF (= contestn 2)
      (setq varprvn (+ varprvn 1))
      (setq varprvn (+ varprvn contestn))
    )
  )
  (setq contestn (1+ contestn))
)

(defun generamatrizc (LISTAcorrelaciones NCORRELA nestactbl)
  (setq contestnr 1)
  (setq varprvn NCORRELA)
  (setq varprvn2 NCORRELA)
  (setq descu1 1)
  (setq descu2 2)
  (setq resultado "")
  (repeat nestactbl
    (setq contestn 1)
    (repeat (1- contestnr)
      (setq varprvn2x (+ varprvn2 (1- contestn)))
      (setq resultado (strcat resultado (substr LISTAcorrelaciones (1+ (* 20 (1- varprvn2x))) 20)))
      (setq contestn (1+ contestn))
    )
    (if (> contestnr 1)
      (progn
        (setq varprvn2 (- varprvn2 descu2))
        (setq descu2 (1+ descu2))
        (setq contestn (1+ contestn))
      )
      (setq contestn (1+ contestn))
    )
    (setq resultado (strcat resultado "xxxxxxxxxxxxxxxxxxxx"))
    (setq varprvn2x varprvn)
    (setq bandera 0)
    (repeat (- nestactbl contestnr)
      (if (= bandera 1)
        (setq varprvn2x (- varprvn2x (1- contestn)))
        (setq bandera 1)
      )
      (setq resultado (strcat resultado (substr LISTAcorrelaciones (1+ (* 20 (1- varprvn2x))) 20)))
      (setq contestn (1+ contestn))
    )
    (setq varprvn (- varprvn descu1))
    (setq descu1 (1+ descu1))
    (setq contestnr (1+ contestnr))
  )
  (setq resultado resultado)
)
