(DEFUN desencripta (textoenc clave)
  (setq er "")
  (setq cr "")
  (setq anchoclave (strlen clave))
  (if (> anchoclave 0)
    (progn
      (setq conti 1)
      (repeat (strlen textoenc)
        (setq cad1 (ascii (substr textoenc conti 1)))
        (if (> conti anchoclave)
          (setq Cad2 (Ascii (substr clave (1+ (rem conti anchoclave)) 1)))
          (setq cad2 (Ascii (substr clave conti 1)))
        )
        (setq cad1 (- cad1 cad2 64))
        (if (< cad1 0) (setq cad1 (+ 256 cad1)))
        (setq cr (strcat cr (chr cad1)))
        (setq conti (1+ conti))
      )
    )
    (setq cr textoenc)
  )
  (setq cr cr)
)

;(encripta "cadena" "1234")
