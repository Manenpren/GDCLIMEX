(DEFUN CARTAING (COORDENADA)
  (SETQ LONGITUD (ATOF (RTOS (CAR COORDENADA) 2 12)))
  (SETQ LATITUD (ATOF (RTOS (CADR COORDENADA) 2 12)))
  (SETQ HUSO (FIX (+ (/ LONGITUD 6) 31)))
  (SETQ LETRAINICIAL (CHR (+ 65 (FIX (/ LATITUD 4)))))
  (SETQ DISTMERIDIANO (- (* (- HUSO 31) 6) LONGITUD))                                  ;x
  (SETQ DISTMERIDIANO2 (- 4 (- latitud (* (FIX (/ LATITUD 4)) 4))))                    ;y
  (SETQ XCARTA (FIX (/ (ABS DISTMERIDIANO) 2)))
  (setq numerocarta25 (fix (+ XCARTA (* 3 DISTMERIDIANO2))))
  (SETQ CARTA25 (strcat letrainicial (itoa huso) "-" (itoa numerocarta25)))
  (IF (> (ABS DISTMERIDIANO) 3) (SETQ CONTADOR2 2) (SETQ CONTADOR2 1))
  (IF (> (ABS DISTMERIDIANO2) 2) (SETQ CONTADOR1 2) (SETQ CONTADOR1 1))
  (IF (AND (= CONTADOR1 2) (= CONTADOR2 1)) 
    (SETQ LETRAFINAL "C")
    (SETQ LETRAfinAL (CHR (+ 64 (* CONTADOR1 CONTADOR2))))
  )
;  (setq ycerrada (- 4 (- latitud (* 4 (fix (/ LATITUD 4)))))
  (SETQ DISTMERIDIANO3 (- 4 (- latitud (* 4 (fix (/ LATITUD 4))))))
  (SETQ DISTMERIDIANO4 (- (* (- HUSO 31) 6) (* (FIX (/ LONGITUD 0.33333333333333333)) 0.33333333333333333)))
  (IF (> (abs DISTMERIDIANO3) 2) (SETQ DISTMERIDIANO3 (- (ABS DISTMERIDIANO3) 2)))
  (IF (> (abs DISTMERIDIANO4) 3) (SETQ DISTMERIDIANO4 (- (ABS DISTMERIDIANO4) 3)))
  (SETQ XCARTA50 (/ DISTMERIDIANO4 0.33333333333333333))
  (SETQ YCARTA50  (atoi (rtos (fix (1+ (/ DISTMERIDIANO3 0.25))) 2 0)))
  (SETQ NUMEROCARTA50 (+ (ABS XCARTA50) (* 10 YCARTA50)))
  (setq nombre (strcat letrainicial (itoa huso) LETRAFINAL (RTOS NUMEROCARTA50 2 0)))
;  (SETQ MERIDIANOHUSO (- (* HUSO 6) 183))
;  (SETQ DELTALAMBDA (- LONGITUDR (/ (* 3.14159265359 MERIDIANOHUSO) 180.000000000)))
)
