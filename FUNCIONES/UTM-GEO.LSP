(DEFUN UTM-GEO (COORDENADA ZONAHORARIA)
  (SETQ EXENTRICIDAD 0.081819191)
  (SETQ EXENTRICIDAD2 0.082094438)
  (SETQ EXENTRICIDAD22 0.006739497)
  (SETQ C 6399593.626)
  (SETQ APLASTAMIENTO 0.0033528107)
  (SETQ X (ATOF (RTOS (CAR COORDENADA) 2 12)))
  (SETQ Y (ATOF (RTOS (CADR COORDENADA) 2 12)))
  (SETQ X (- 500000.000000 X))
  (SETQ MERIDIANOCENTRAL (- (* ZONAHORARIA 6) 183))
  (SETQ FI (/ Y (* 6366197.7240000 0.99960000)))
  (SETQ COSENOFI (COS FI))
  (SETQ COSENOFI2 (EXPT COSENOFI 2))
  (SETQ V (* (/ C (sqrt (1+ (* EXENTRICIDAD22 COSENOFI2)))) 0.9996000))
  (SETQ A (/ X V))
  (SETQ A1 (SIN (* 2 FI)))
  (SETQ A2 (* A1 COSENOFI2))
  (SETQ J2 (+ FI (/ A1 2)))
  (SETQ J4 (/ (+ (* 3 J2) A2) 4))
  (SETQ J6 (/ (+ (* 5 J4) (* A2 COSENOFI2)) 3))
  (SETQ ALPHA (* (/ 3.00000000 4.00000000) EXENTRICIDAD22))
  (SETQ BETA (* (/ 5.00000000 3.00000000) (EXPT ALPHA 2)))
  (SETQ GAMA (* (/ 35.00000000 27.00000000) (EXPT ALPHA 3)))
  (SETQ BCERO (* 0.9996 C (+ FI (* -1 ALPHA J2) (* BETA J4) (* -1 GAMA J6))))
  (SETQ B (/ (- Y BCERO) V))
  (setq ZETA (* (/ (* EXENTRICIDAD22 (EXPT A 2)) 2) COSENOFI2))
  (setq tao (* a (1- (/ zeta 3))))
  (SETQ N (+ (* (- 1 ZETA) B) FI))
  (setq senohfi (/ (- (exp tao) (exp (* tao -1))) 2))
  (setq incrementogm (atan (/ senohfi (cos n))))
  (setq tao2 (atan (* (cos incrementogm) (tan n))))
  (setq longitud (+ (/ (* incrementogm 180) 3.14159265359) meridianocentral))
  (setq latitud (+ fi (* (+ 1 (* exentricidad22 cosenofi2)  (* -1 (/ 3 2) exentricidad22 (sin fi) cosenofi (- tao2 fi))) (- tao2 fi))))
  (setq latitud (/ (* 180 latitud) 3.14159265359))
  (SETQ PUNTOFINAL (LIST LONGITUD LATITUD))
)

(defun tan (z / cosz)
  (if (zerop (setq cosz (cos z)))
    *INF*    
    (/ (sin z) cosz)
  )
)
