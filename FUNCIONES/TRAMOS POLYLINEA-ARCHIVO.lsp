(defun TRPOL (linea)
  (C:LIBRERIA "vertices de una lwpolyline to var")
  (setq vertices (verticebd LINEA))
  (setq P1T (cdr (assoc 0 vertices)))
  (setq cuever 0)
  (SETQ XMENOR (CAR P1T))
  (SETQ YMENOR (CADR P1T))
  (SETQ XMAYOR XMENOR)
  (SETQ YMAYOR YMENOR)
  (SETQ PROVV P1T)
  (while p1t
    (SETQ X2PROV (CAR P1T))
    (SETQ Y2PROV (CADR P1T))
    (IF (AND (< X2PROV XMENOR) (/= X2PROV nil)) (SETQ XMENOR X2PROV))
    (IF (AND (< Y2PROV YMENOR) (/= Y2PROV nil)) (SETQ YMENOR Y2PROV))
    (IF (AND (> X2PROV XMAYOR) (/= X2PROV nil)) (SETQ XMAYOR X2PROV))
    (IF (AND (> Y2PROV YMAYOR) (/= Y2PROV nil)) (SETQ YMAYOR Y2PROV))
    (SETQ cuever (1+ cuever))
    (setq P1T (cdr (assoc cuever vertices)))
  )
  (setq dosx (* (- xmayor xmenor) 0.15))
  (setq dosy (* (- ymayor ymenor) 0.15))
  (COMMAND "ZOOM" "W" (STRCAT (RTOS (- XMENOR dosx) 2 6) "," (RTOS (- YMENOR dosy) 2 6)) (STRCAT (RTOS (+ XMAYOR dosx) 2 6) "," (RTOS (+ YMAYOR dosy) 2 6)))
  (command "copy" linea "" "0,0" "0,0")
  (SETQ PRV (cdr (assoc 0 (entget linea))))
  (SETQ PRV (STRCASE PRV))
  (IF (=  PRV "LWPOLYLINE") 
    (PROGN
      (command "explode" (entlast))
      (setq gpoacot (ssadd))
      (setq gpoacot (ssget "p"))
    )
    (SETQ GPOACOt (SSADD LINEA))
  )
  (SETQ E (SSNAME GPOACOT 0))
  (setq cont 0)
  (SETQ matrizpol NIL)
  (SETQ f1 (OPEN "C:\\prov\\TRAMOS.CSV" "w"))
  (WHILE E
    (SETQ PRV (cdr (assoc 0 (entget E))))
    (SETQ PRV (STRCASE PRV))
    (IF (= PRV "ARC")
      (PROGN
        (SETQ RADIO (cdr (assoc 40 (entget e))))
        (SETQ RADIOx (cdr (assoc 10 (entget e))))
        (SETQ Yr (CADR radiox))
        (SETQ Xr (CAR radiox))
        (SETQ ANGINI (cdr (assoc 50 (entget e))))
        (SETQ ANGF (cdr (assoc 51 (entget e))))
        (setq xc1 (+ xr (* radio (cos angini))))
        (setq yc1 (+ yr (* radio (sin angini))))
        (setq xc2 (+ xr (* radio (cos angf))))
        (setq yc2 (+ yr (* radio (sin angf))))
        (setq xyz (list xc1 yc1))
        (setq xyz2 (list xc2 yc2))
        (IF (< ANGINI ANGF)
          (PROGN
            (SETQ DIF (- ANGF ANGINI))
            (setq ang2 (+ angini (/ dif 2)))
          )
          (PROGN
            (SETQ ANGF (+ ANGF 6.28318530718))
            (SETQ DIF (- ANGF ANGINI))
            (setq ang2 (+ angini (/ dif 2)))
          )
        )
        (setq xc3 (+ xr (* radio (cos ang2))))
        (setq yc3 (+ yr (* radio (sin ang2))))
        (SETQ DISTANCIA (* RADIO DIF))
        (setq CONCATENADO (cons CONT (list "A" (list angini angf radio) radiox distancia))) ;'(ANGIN) '(ANFIN) '(RADIO) (centro)
        (WRITE-LINE (strcat "A," (rtos ANGINI) "," (rtos ANGF) "," (rtos RADIO) "," (rtos XR) ","  (rtos YR) "," (rtos DISTANCIA)) F1)
        (setq matrizpol (append matrizpol (list CONCATENADO)))
      )
    )
    (IF (= PRV "LINE")
      (PROGN
        (SETQ xyz (cdr (assoc cont vertices)))
        (SETQ xyz2 (cdr (assoc (1+ cont) vertices)))
        (SETQ Y1 (CADR XYZ))
        (SETQ X1 (CAR XYZ))
        (SETQ Y2 (CADR XYZ2))
        (SETQ X2 (CAR XYZ2))
        (setq distancia (distance xyz xyz2))
        (setq CONCATENADO (cons CONT (list "L" xyz xyz2 distancia)))
        (WRITE-LINE (strcat "L," (rtos X1) "," (rtos Y1) "," (rtos X2) "," (rtos Y2) "," (rtos DISTANCIA)) F1)
        (setq matrizpol (append matrizpol (list CONCATENADO)))
      )
    )
    (SETQ CONT (1+ CONT))
    (SETQ E (SSNAME GPOACOT cont))
  );WHILE
  (close f1)
  (command "erase" gpoacot "")
  (setq matrizpol matrizpol)
);(setq x (trpol (car (entsel))))
