(DEFUN ESTERIC (GMIN GMAX)
  (C:LIBRERIA "SEPARA VALORES DE COMAS DE UN TEXTO TO LISTA")
  (C:LIBRERIA "lee concentrado estaciones")
  (SETQ LONG1 (RTOS (car GMIN) 2 5))
  (SETQ LAT1 (RTOS (caDr GMIN) 2 5))
  (SETQ LONG2 (RTOS (car GMAX) 2 5))
  (SETQ LAT2 (RTOS (caDr GMAX) 2 5))
  (SETQ matrizeST NIL)
  (SETQ matrizporcentaje NIL)
  (cargamem2)
  (SETQ NEST 1)
  (setq lINEAfUENTE (substr bdmemeric 1 58))
  (setq nrepeticion (/ (strlen BDMEMeric) 58))
  (setq indiceeric "")
  (setq contci2 1)
  (repeat nrepeticion
    (if (< contanim 6064)
      (anim) 
    )
    (setq LATES (substr lINEAfUENTE 30 12))
    (setq LONGES (substr lINEAfUENTE 42 13))
    (IF (AND (> (ATOF LATES) (ATOF LAT1)) (< (ATOF LATES) (ATOF LAT2)) (> (ATOF LONGES) (ATOF LONG1)) (< (ATOF LONGES) (ATOF LONG2))) 
      (PROGN
        (setq CVEST (substr lINEAfUENTE 1 5))
        (setq CONCATENADO (cons neST (list CVEST longes lates)))
        (setq matrizEST (append matrizEST (list CONCATENADO)))
        (setq valorx (leeconcentrado cvest "E"))
        (setq CONCATENADO (cons neST valorx))
        (setq matrizporcentaje (append matrizporcentaje (list CONCATENADO)))
        (setq indiceeric (strcat indiceeric (ntocad contci2 0 6)))
        (SETQ NEST (1+ NEST))
      )
    )
    (setq lINEAfUENTE (substr bdmemeric (+ 1 (* contci2 58)) 58))
    (SETQ contci2 (1+ contci2))
  );WHILE
  (if (/= archivocl nil)
    (close archivocl)
  )
  (setq nesteric (1- nest))
  (SETQ MATRIZEST MATRIZEST)
)

(defun cargamem2 ()
  (if (= bdmemeric nil)
    (progn
      (dos_getcancel "LEYENDO BD" "LEYENDO DATOS POR FAVOR ESPERE...")
      (setq bdmemeric "")
      (setq archIVOCL (open (strcat ruta "BASES DE DATOS\\DATOS CLIMATOLOGICOS\\ESTACIONES\\ERIC.CSV") "r"))
      (setq lINEAfUENTE (read-line archIVOCL))
      (SETQ NEST 1)
      (while (/= lineafuente nil)
        (SETQ VALORES (SEPARA_VAL_COMAS LINEAFUENTE))
        (setq bdmemeric (strcat bdmemeric (CADTOCAD (cdr (assoc 1 valores)) " " 5) (CADTOCAD (cdr (assoc 2 valores)) " " 24) (CADTOCAD (cdr (assoc 3 valores)) " " 12) (CADTOCAD (cdr (assoc 4 valores)) " " 13) (CADTOCAD (cdr (assoc 5 valores)) " " 4)))
        (setq lINEAfUENTE (read-line archIVOCL))
      );WHILE
      (IF (not (dos_getcanceL)) (exit))
      (dos_getcanceL t)
    )
  )
)
