(defun C:CREA ()
    (repeat 4
        (setq bl (car (entsel "Selecciona EL BLOCK: ")))
        (setq bl (entnext bl))
        (setq nombre (cdr (assoc 1 (entget bl))))
        (if (= "BASE" (substr nombre 1 4))
            (setq bl (entnext bl))
            (setq BASE (cdr (assoc 1 (entget bl))))
        )
        (if (= "SUBR" (substr nombre 1 4))
            (setq bl (entnext bl))
            (setq SUBRAS (cdr (assoc 1 (entget bl))))
        )
        (if (= "FILT" (substr nombre 1 4))
            (setq bl (entnext bl))
            (setq FILTRO (cdr (assoc 1 (entget bl))))
        )
        (if (= "CARP" (substr nombre 1 4))
            (setq bl (entnext bl))
            (setq CARPETA (cdr (assoc 1 (entget bl))))
        )
    )
    (SETQ XYZ (GETPOINT " PUNTO DE INSERCION : "))
    (COMMAND "INSERT" "VOLUMENES" XYZ "" "" "" CARPETA BASE SUBRAS FILTRO FILTRO)
)
