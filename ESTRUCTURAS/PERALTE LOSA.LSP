(DEFUN C:PLOZA ()
     (SETQ XYZ (GETPOINT "DAME UN PUNTO AL CENTRO DEL AREA: "))
     (COMMAND "-BOUNDARY" XYZ "")
     (COMMAND "AREA" "E" "L")
     (SETQ AP (RTOS (GETVAR "PERIMETER") 2 3))
  (SETQ XYZX (CONS 10 XYZ))
  (SETQ XYZX2 (CONS 11 XYZ))
  (setq tamanot (cons 40 0.3))
  (setq layert (cons 8 "0"))                            
  (setq nivel2 (car (cdr nivel)))
  (SETQ TEXTX (CONS 1 (strcat "h=" AP "/200=" (RTOS (/ (ATOF AP) 200) 2 3))))
  (ENTMAKE (LIST '(0 . "TEXT") '(100 . "AcDbEntity") layert '(100 . "AcDbText") XYZX tamanot TEXTX '(7 . "ROMANS") '(72 . 1) xyzx2 '(73 . 1)))
)

(DEFUN C:PLOZA ()
     (SETQ XYZ (GETPOINT "DAME UN PUNTO AL CENTRO DEL AREA: "))
     (COMMAND "-BOUNDARY" XYZ "")
     (COMMAND "AREA" "E" "L")
     (SETQ AP (RTOS (GETVAR "PERIMETER") 2 3))
  (SETQ XYZX (CONS 10 XYZ))
  (SETQ XYZX2 (CONS 11 XYZ))
  (setq tamanot (cons 40 0.3))
  (setq layert (cons 8 "0"))                            
  (setq nivel2 (car (cdr nivel)))
  (SETQ TEXTX (CONS 1 (strcat "h=" AP "/200=" (RTOS (/ (ATOF AP) 200) 2 3))))
  (ENTMAKE (LIST '(0 . "TEXT") '(100 . "AcDbEntity") layert '(100 . "AcDbText") XYZX tamanot TEXTX '(7 . "ROMANS") '(72 . 1) xyzx2 '(73 . 1)))
)
