;PROGRAMA PARA CALCULAR AREAS DE PREDIOS E INSERTAR NOMBRE DE PROPIETARIO
;SE REQUIERE CREAR UN BLOCK "NOMAR" CON ATRIBUTOS "NOMBRE" Y "AREA" CON
;ALTURA DE 1 Y CENTRADOS EN 0,0 NOMBRE SOBRE AREA
:CREAR PREVIO AL PROGRAMA EL LAYER "AREAS"
(DEFUN C:CA ()
     (C:LIBRERIA "CENTROIDE DE UN POLIGONO IRREGULAR2")
     (SETQ N (GETSTRING PROMPT "DAME EL NOMBRE DEL PROPIETARIO: "))
     (SETQ XYZ (GETPOINT "DAME UN PUNTO AL CENTRO DEL AREA: "))
     (COMMAND "-BOUNDARY" XYZ "")
     (COMMAND "CHANGE" "L" "" "P" "LA" "AREAS" "")
     (COMMAND "AREA" "E" "L")
     (SETQ AP (RTOS (GETVAR "AREA") 2 3))
     (setq xyz (ax:centroid (entlast)))
     (COMMAND "INSERT" (strcat ruta "blocks\\NOMAR") XYZ "" "" "" N AP)
     (SETQ ENTP (ENTLAST))
     (SETQ ENTP (ENTNEXT ENTP))
     (COMMAND "ATTEDIT" "" "" "" "" ENTP "V" "R" N "")
     (SETQ ENTP (ENTNEXT ENTP))
     (COMMAND "ATTEDIT" "" "" "" "" ENTP "V" "R" AP "")
)

(DEFUN C:CORTE ()
     (C:LIBRERIA "CENTROIDE DE UN POLIGONO IRREGULAR2")
     (SETQ XYZ (GETPOINT "DAME UN PUNTO AL CENTRO DEL AREA: "))
     (SETQ XYZ1 XYZ)
     (SETQ AP 0)
     (WHILE XYZ
       (COMMAND "-BOUNDARY" XYZ "")
       (COMMAND "CHANGE" "L" "" "P" "LA" "AREAS" "")
       (COMMAND "AREA" "E" "L")
       (SETQ EX (ENTLAST))
       (SETQ AP (+ AP (GETVAR "AREA")))
       (SETQ XYZ (GETPOINT "DAME UN PUNTO AL CENTRO DEL AREA: <SALIR> "))
       (COMMAND "ERASE" EX "")
     )
     (SETQ AP (RTOS AP 2 3))
;     (setq xyz (ax:centroid (entlast)))
     (COMMAND "INSERT" (strcat ruta "blocks\\NOMAR") XYZ1 "" "" "")
     (SETQ ENTP (ENTLAST))
     (SETQ ENTP (ENTNEXT ENTP))
     (COMMAND "ATTEDIT" "" "" "" "" ENTP "V" "R" "CORTE" "")
     (SETQ ENTP (ENTNEXT ENTP))
     (COMMAND "ATTEDIT" "" "" "" "" ENTP "V" "R" AP "")
)

(DEFUN C:TERRAP ()
     (C:LIBRERIA "CENTROIDE DE UN POLIGONO IRREGULAR2")
     (SETQ XYZ (GETPOINT "DAME UN PUNTO AL CENTRO DEL AREA: "))
     (SETQ XYZ1 XYZ)
     (SETQ AP 0)
     (WHILE XYZ
       (COMMAND "-BOUNDARY" XYZ "")
       (COMMAND "CHANGE" "L" "" "P" "LA" "AREAS" "")
       (COMMAND "AREA" "E" "L")
       (SETQ EX (ENTLAST))
       (SETQ AP (+ AP (GETVAR "AREA")))
       (SETQ XYZ (GETPOINT "DAME UN PUNTO AL CENTRO DEL AREA: <SALIR> "))
       (COMMAND "ERASE" EX "")
     )
     (SETQ AP (RTOS AP 2 3))
;     (setq xyz (ax:centroid (entlast)))
     (COMMAND "INSERT" (strcat ruta "blocks\\NOMAR") XYZ1 "" "" "")
     (SETQ ENTP (ENTLAST))
     (SETQ ENTP (ENTNEXT ENTP))
     (COMMAND "ATTEDIT" "" "" "" "" ENTP "V" "R" "TERRAP" "")
     (SETQ ENTP (ENTNEXT ENTP))
     (COMMAND "ATTEDIT" "" "" "" "" ENTP "V" "R" AP "")
)

(DEFUN C:DPC ()
     (C:LIBRERIA "CENTROIDE DE UN POLIGONO IRREGULAR2")
     (SETQ XYZ (GETPOINT "DAME UN PUNTO AL CENTRO DEL AREA: "))
     (SETQ XYZ1 XYZ)
     (SETQ AP 0)
     (WHILE XYZ
       (COMMAND "-BOUNDARY" XYZ "")
       (COMMAND "CHANGE" "L" "" "P" "LA" "AREAS" "")
       (COMMAND "AREA" "E" "L")
       (SETQ EX (ENTLAST))
       (SETQ AP (+ AP (GETVAR "AREA")))
       (SETQ XYZ (GETPOINT "DAME UN PUNTO AL CENTRO DEL AREA: <SALIR> "))
       (COMMAND "ERASE" EX "")
     )
     (SETQ AP (RTOS AP 2 3))
;     (setq xyz (ax:centroid (entlast)))
     (COMMAND "INSERT" (strcat ruta "blocks\\NOMAR") XYZ1 "" "" "" "DC" AP)
)

(DEFUN C:DPT ()
     (C:LIBRERIA "CENTROIDE DE UN POLIGONO IRREGULAR2")
     (SETQ XYZ (GETPOINT "DAME UN PUNTO AL CENTRO DEL AREA: "))
     (SETQ XYZ1 XYZ)
     (SETQ AP 0)
     (WHILE XYZ
       (COMMAND "-BOUNDARY" XYZ "")
       (COMMAND "CHANGE" "L" "" "P" "LA" "AREAS" "")
       (COMMAND "AREA" "E" "L")
       (SETQ EX (ENTLAST))
       (SETQ AP (+ AP (GETVAR "AREA")))
       (SETQ XYZ (GETPOINT "DAME UN PUNTO AL CENTRO DEL AREA: <SALIR> "))
       (COMMAND "ERASE" EX "")
     )
     (SETQ AP (RTOS AP 2 3))
;     (setq xyz (ax:centroid (entlast)))
     (COMMAND "INSERT" (strcat ruta "blocks\\NOMAR") XYZ1 "" "" "" "DT" AP)
)

(DEFUN C:CA2 ()
   (C:LIBRERIA "CENTROIDE DE UN POLIGONO IRREGULAR2")
   (SETQ N (GETint "Numero de inicio: "))
   (while xyz
     (SETQ XYZ (GETPOINT "DAME UN PUNTO AL CENTRO DEL AREA: "))
     (if (/= xyz nil)
      (progn
        (COMMAND "-BOUNDARY" XYZ "")
        (COMMAND "CHANGE" "L" "" "P" "LA" "AREAS" "")
        (COMMAND "AREA" "E" "L")
        (SETQ AP (RTOS (GETVAR "AREA") 2 3))
        (setq xyz (ax:centroid (entlast)))
        (COMMAND "INSERT" (strcat ruta "blocks\\NOMAR") XYZ "" "" "" N AP)
        (setq n (1+ n))
      )
     )
   )
)
