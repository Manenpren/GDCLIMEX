(defun C:PENDIENTE1 ()
  (setq E (CAR (ENTSEL " LINEA PARA CALCULAR SU PENDIENTE ")))
  (setq pun1 (cdr (assoc 10 (entget E)))) 
  (setq pun2 (cdr (assoc 11 (entget E)))) 
  (setq x1 (car pun1))
  (setq y1 (car (cdr pun1)))
  (setq x2 (car pun2))
  (setq y2 (car (cdr pun2)))
  (setq xd (- x1 x2))
  (if (> 0 xd)
    (setq xd (* xd -1))
  )
  (setq xd (/ xd 2))

  (setq yd (- y1 y2))
  (if (> 0 yd)
    (setq yd (* yd -1))
  )
  (setq yd (/ yd 2))
  (if (> x1 x2)
    (setq xd (+ xd x2))
    (setq xd (+ xd x1))
  )
  (if (> y1 y2)
    (setq yd (+ yd y2))
    (setq yd (+ yd y1))
  )
  (setq punmid (list xd yd))  
  (SETQ YM (- Y1 Y2))
;  (SETQ YM (/ YM 10))
  (SETQ XM (- X1 X2))
  (SETQ M (/ YM XM))
  (IF (> M 0) (SETQ SIGNO "+") (SETQ SIGNO ""))
  (SETQ M (RTOS M 2 3))
  (SETQ M (STRCAT SIGNO M " %"))
  (if (> X1 X2) 
    (SETQ ORR (list x1 y1))
    (SETQ ORR (list x2 y2))
  )
  (SETQ PUNMID (SUMA PUNMID 0.5 0.5))
  (SETQ ORR (SUMA ORR 0.5 0.5))
  (SETQ XYZX (CONS 10 PUNMID))
  (SETQ TEXTX (CONS 1 M))
  (ENTMAKE (LIST '(0 . "TEXT") '(100 . "AcDbEntity") '(8 . "0") '(100 . "AcDbText") XYZX '(40 . 1) TEXTX))
;  (COMMAND "INSERT" (STRCAT RUTA "BLOCKS\\TEXTO") PUNMID "" "" ORR)
;  (COMMAND "EXPLODE" "L" "")
;  (COMMAND "CHANGE" "L" "" "" "" "" "" "" M)
)

(defun suma (punto xx yy)
  (setq xxx (car punto))
  (setq yyy (car (cdr punto)))
  (setq xxx (+ xxx xx))
  (setq yyy (+ yyy yy))
  (list xxx yyy)
)
