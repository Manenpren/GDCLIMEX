(defun c:wtx ()
  (command "undo" "m")
  (C:LIBRERIA "BUSCA VALOR DE ATRIBUTO")
  (setq rutawb "c:\\topograf\\chapadr\\")
  (SETQ RUTAWB2 (GETSTRING (STRCAT "\n RUTA A DESCARGAR <" RUTAWB "> :")))
  (IF (/= RUTAWB2 "") 
    (SETQ RUTAWB RUTAWB2)
  )
  (SETQ GPONOMNUM (SSADD))
  (SETQ GPONOMNUM (SSGET "X" '((2 . "NOMNUM"))))
  (SETQ E (SSNAME GPONOMNUM 0))
  (SETQ G 1)
  (WHILE E
;   (SETQ X (CAR PUNTO))
;   (IF (/= X 0)
;    (PROGN
     (SETQ XYZ2 (cdr (assoc 10 (entget E))))
     (SETQ NLOT (BUSATR E "NO-LOTE"))
     (IF (= NLoT NIL)
       (setq nlot (busatr e "NO_LOTE"))
     )
     (setq nlot (strcat "DL-" nlot))
     (SETQ P1 (SUMA XYZ2 -300 -300))
     (SETQ P2 (SUMA XYZ2 -300 300))
     (SETQ P3 (SUMA XYZ2 300 300))
     (SETQ P4 (SUMA XYZ2 300 -300))
     (command "wblock" (STRCAT RUTAWB2 "\\" NLOT ".DWG") "" "0,0,0" "CP" P1 P2 P3 P4 "" "")
     (command "u")
     (SETQ NLOT NIL)
;    )
;   )
  (SETQ E (SSNAME GPONOMNUM G))
  (SETQ G (1+ G))
  )
)

(defun SUMA (punto xx yy)
  (setq x (car punto))
  (setq y (car (cdr punto)))
  (setq xxx (+ x xx))
  (setq yyy (+ y yy))
  (list xxx yyy)
)
