(defun c:exc3d ()
  (C:LIBRERIA "SEPARA VALORES DE COMAS DE UN TEXTO TO LISTA")
  (setq bdmemclicom nil)
  (COMMAND "UNDO" "M")
  (cargamemc)
  (command "osnap" "none")
  (setq arcdes (getfiled "ARCHIVO DE Descarga" "*." "csv" 19))
  (print "\n Seleciona los elementos a procesar ")
  (SETQ f1 (OPEN arcdes "w"))
  (setq gpo (ssget '((8 . "CVL_SECC_CUAD"))))
  (SETQ P2 0)  
  (SETQ PROV (SSNAME GPO P2))
  (SETQ AO (ENTGET PROV))
  (WHILE (/= PROV NIL)
    (SETQ xyz (cdr (assoc 10 AO)))
    (SETQ xyz2 (cdr (assoc 11 AO)))
    (setq punver1 (suma xyz -0.01 -0.01))
    (setq punver2 (suma xyz 0.01 0.01))
    (command "ZOOM" "W" punver1 punver2)
    (setq ss1 (ssget "C" punver1 punver2 '((8 . "CVL_SECC_CUAD"))))
    (setq punver1 (suma xyz2 -0.01 -0.01))
    (setq punver2 (suma xyz2 0.01 0.01))
    (command "ZOOM" "W" punver1 punver2)
    (setq ss2 (ssget "C" punver1 punver2 '((8 . "CVL_SECC_CUAD"))))
    (ssdel PROV ss1)
    (ssdel PROV ss2)
    (SETQ xyz (cdr (assoc 10 AO)))
    (SETQ xyz2 (cdr (assoc 11 AO)))
    (SETQ Xp1 (CAR xyz))
    (SETQ Yp1 (CADR xyz))
    (SETQ Xp2 (CAR xyz2))
    (SETQ Yp2 (CADR xyz2))
    (setq xminp xp1)
    (setq yminp yp1)
    (setq xmaxp xp1)
    (setq ymaxp yp1)
    (maximos xp1 yp1)
    (maximos xp2 yp2)
    (SETQ xyz (cdr (assoc 10 (entget (SSNAME ss1 0)))))
    (SETQ xyz2 (cdr (assoc 11 (entget (SSNAME ss1 0)))))
    (SETQ Xp1 (CAR xyz))
    (SETQ Yp1 (CADR xyz))
    (SETQ Xp2 (CAR xyz2))
    (SETQ Yp2 (CADR xyz2))
    (maximos xp1 yp1)
    (maximos xp2 yp2)
    (SETQ xyz (cdr (assoc 10 (entget (SSNAME ss2 0)))))
    (SETQ xyz2 (cdr (assoc 11 (entget (SSNAME ss2 0)))))
    (SETQ Xp1 (CAR xyz))
    (SETQ Yp1 (CADR xyz))
    (SETQ Xp2 (CAR xyz2))
    (SETQ Yp2 (CADR xyz2))
    (maximos xp1 yp1)
    (maximos xp2 yp2)
    (command "ZOOM" "W" (suma (list xmaxp ymaxp) 10 10) (suma (list xminp yminp) -10 -10))
    (setq ssdl (ssget "C" (list xmaxp ymaxp) (list xminp yminp) '((8 . "CVL_SECC_CUAD"))))
    (setq contx 0)
    (repeat 4
      (SETQ entx (SSNAME ssdl contx))
      (ssdel entx gpo)
      (setq contx (1+ contx))
    )
    (createxto)
    (SETQ PROV (SSNAME GPO P2))
    (IF (/= PROV NIL)
       (SETQ AO (ENTGET PROV))
    )
  )
  (close f1)
)

(defun maximos (xpx ypx)
    (if (> xpx xmaxp) (setq xmaxp xpx))
    (if (< xpx xminp) (setq xminp xpx))
    (if (> ypx ymaxp) (setq ymaxp ypx))
    (if (< ypx yminp) (setq yminp ypx))
)

(defun createxto ()
  (setq ssec (ssget "C" (suma (list xmaxp ymaxp) 2 2) (suma (list xminp yminp) -2 -2)))
  (setq sspr (ssget "C" (list xmaxp ymaxp) (list xminp yminp) '((8 . "topografia definitiva"))))
  (setq sstxt (ssget "C" (suma (list xmaxp ymaxp) 8 8) (suma (list xminp yminp) -8 -8) '((8 . "CVL_SECC_TX"))))
  (setq sscadena (ssget "C" (suma (list xmaxp ymaxp) 2 2) (suma (list xminp yminp) -2 -2) '((8 . "cadenamientos"))))
  (SETQ P2c 0)  
  (SETQ PROVc (SSNAME sstxt P2c))
  (SETQ AOc (ENTGET PROVc))
  (WHILE (/= PROVc NIL)
    (SETQ xyzx (cdr (assoc 10 AOc)))
    (SETQ Xpc (CAR xyzx))
    (setq p2c (1+ p2c))
    (SETQ PROVc (SSNAME sstxt P2c))
    (if (< xpc xminp) (setq provc nil))
    (IF (/= PROVc NIL)
       (SETQ AOc (ENTGET PROVc))
    )
  )
  (setq elev (cdr (assoc 1 (ENTGET (SSNAME sstxt P2c)))))
  (setq elevf (CADR (cdr (assoc 10 (ENTGET (SSNAME sstxt P2c))))))
  (setq elevf (+ elevf 0.5))
  (setq contr 1)
  (setq elevcr "")
  (repeat (strlen elev)
    (setq carx (substr elev contr 1))
    (if (/= "," carx) (setq elevcr (strcat elevcr carx)))
    (setq contr (1+ contr))
  )
  (setq ejec (+ xminp (/ (- xmaxp xminp) 2)))
  (setq caden (cdr (assoc 1 (ENTGET (SSNAME sscadena 0)))))

  (setq lin (SSNAME sspr 0))
  (setq f 0)
  (SETQ VER1 "")
  (while ver1
     (setq f (1+ f))
     (SETQ VER1 (vertice lin f)) 
  )
  (setq f (1- f))
  (setq J 1)
  (setq elevs "1")
  (setq CODEs "V")
  (SETQ VER2 (vertice lin 1))
  (setq verh ver2)
  (REPEAT (1- f)
     (setq J (1+ J))
     (SETQ VER1 (vertice lin J))
     (IF (/= VER1 NIL)
       (progn
         (if (= "volteado" (CADdR (CDDDDR (assoc (atoi caden) bdmemclicom))))
            (setq xf (+ (* (- ejec (car ver1)) (atof (cadr (assoc (atoi caden) bdmemclicom)))) (atof (CAR (CDDDDR (assoc (atoi caden) bdmemclicom))))));=A3*(-1*D3)+F3
            (setq xf (+ (* (- ejec (car ver1)) (* -1 (atof (cadr (assoc (atoi caden) bdmemclicom))))) (atof (CAR (CDDDDR (assoc (atoi caden) bdmemclicom))))));=A3*(-1*D3)+F3
         )
         (if (= "volteado" (CADdR (CDDDDR (assoc (atoi caden) bdmemclicom))))
            (setq yf (+ (* (- ejec (car ver1)) (atof (caddr (assoc (atoi caden) bdmemclicom)))) (atof (CADR (CDDDDR (assoc (atoi caden) bdmemclicom))))));=A3*(-1*E3)+G3
            (setq yf (+ (* (- ejec (car ver1)) (* -1 (atof (caddr (assoc (atoi caden) bdmemclicom))))) (atof (CADR (CDDDDR (assoc (atoi caden) bdmemclicom))))));=A3*(-1*E3)+G3
         )
         (write-line (strcat (rtos (- ejec (car ver1)) 2 3) "," (rtos (+ (atof elev) (- (car (cdr ver1)) elevf)) 2 3) "," (cadddr (assoc (atoi caden) bdmemclicom)) "," (cadr (assoc (atoi caden) bdmemclicom)) "," (caddr (assoc (atoi caden) bdmemclicom)) "," (CAR (CDDDDR (assoc (atoi caden) bdmemclicom))) "," (CADR (CDDDDR (assoc (atoi caden) bdmemclicom))) "," (rtos xf 2 3) "," (rtos yf 2 3)) f1)
         (setq ver2 ver1)
       )
     )
  )
  ;(alert "seccion escaneada")
)

(defun SUMA (punto xx yy)
  (setq x (car punto))
  (setq y (car (cdr punto)))
  (setq xxx (+ x xx))
  (setq yyy (+ y yy))
  (list xxx yyy)
)

(defun vertice (poli nov)
  (setq listap (entget poli))
  (setq nver 0)
  (setq salir "N")
  (while (= salir "N")
    (setq sublisp (car listap))
    (if (= 10 (car sublisp))
      (progn
        (setq punto (cdr sublisp))  
        (setq nver (+ nver 1))
      )
    )
    (setq listap (cdr listap))
    (if listap
      (setq salir "N")
      (setq salir "S")
    )
    (if (= nov nver)
      (setq salir "S")
    )
  )
  (if (not listap)
    (setq punto nil)
  )
  (setq punto punto)
)

(defun cargamemc ()
  (if (= bdmemclicom nil)
    (progn
;      (setq bdmemclicom "")
      (setq archIVOCL (open (strcat ruta "BASES DE DATOS\\CADM.csv") "r"))
      (setq lINEAfUENTE (read-line archIVOCL))
      (SETQ NEST 1)
      (while (/= lineafuente nil)
        (SETQ VALORES (SEPARA_VAL_COMAS LINEAFUENTE))
;        (setq bdmemclicom (strcat bdmemclicom (cdr (assoc 1 valores)) ))
    ;(setq valorx )
      (setq valorcad (atoi (cdr (assoc 4 valores))))
      (setq valorxf (cons valorcad (list (cdr (assoc 2 valores)) (cdr (assoc 3 valores)) (cdr (assoc 1 valores)) (cdr (assoc 5 valores)) (cdr (assoc 6 valores)) (cdr (assoc 7 valores)))))
      (setq bdmemclicom (append bdmemclicom (list valorxf)))
        (setq lINEAfUENTE (read-line archIVOCL))
      );WHILE
    )
  )
)
